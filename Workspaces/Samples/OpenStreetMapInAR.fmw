FME workspace OpenStreetMapInAR.fmw
Title: OpenStreetMapInAR
Description: Purpose & Objectives
This workspace generates an OpenStreetMap dataset based on the user's location in augmented reality using the FME Realize app. Each feature is transformed into a 3D geometry and styled depending on its feature type, and feature summary annotations are created for each feature.
The workspace searches for local landmarks in the immediate user vicinity and expands the search to a wider area if there are no landmarks around. The search radii for local and more remote landmarks can be adjusted in user parameters. 
Key Transformers
AppearanceSetter: Sets appearance style(s) onto the sides of geometry surfaces representing OSM features
HTTPCaller: Makes POST requests to the OSM API to query data for the user's location
Rotator: Rotates features about a specified point in a counterclockwise direction to face the user in AR
Data Source(s) - Reader Feature Type
FeatureReader reads in OSM features from XML file retrieved from OSM API query
Data Output - Writer Feature Type
FeatureWriter writes the XML file returned from the OSM API request as an intermediate step before it is read in as XML
FME AR Writer saves the geometry in FMEAR format that is overlaid on a live view in AR
Customization
To customize this workspace, you can change the following:
Feature appearance (style, colour, texture) with the AppearanceSetter and AppearanceStyler transformers
Attributes to display in AR as summary annotations with the AttributeCreator transformers
Location that displayed OSM features are based on by following the instructions in the Preset Location Testing annotations
If you're recreating this workspace with your own data, it is recommended to build the workspace from scratch as your dataset will have different attributes and schema (structure).
Usage: For help with this workspace, please contact Safe Software Support and reference FME AR: OpenStreetMap in Augmented Reality.

Parameters:
- LOCATION = {	"coordinates": [		-123.1195,		49.2833	],	"type": "Point"}   # GEOM_TYPE:POINT Location
- SEARCHRADIUS = 300   # Search Radius, m
- SEARCHRADIUSEXPANDED =
- EXPANDEDSEARCHRADIUS = 10000   # Expanded Search Radius
- LOCALLANDMARKEXPLANATION =   # Users can control the lowest number of local landmarks, after which the service will try to get landmarks farther away.
- LOCALLANDMARKTHRESHOLD = 15   # Local Landmark Threshold

Readers:
- WEBP_1: WEBP from ""$(FME_MF_DIR)drinking_water.webp" "$(FME_MF_DIR)florist.webp" "$(FME_MF_DIR)memorial.webp" "$(FME_MF_DIR)museum.webp" "$(FME_MF_DIR)parking.webp" "$(FME_MF_DIR)installation.webp" "$(FME_MF_DIR)office.webp" "$(FME_MF_DIR)pharmacy.webp" "$(FME_MF_DIR)university.webp" "$(FME_MF_DIR)waste_basket.webp" "$(FME_MF_DIR)atm.webp" "$(FME_MF_DIR)theatre.webp" "$(FME_MF_DIR)cafe.webp" "$(FME_MF_DIR)restaurant.webp" "$(FME_MF_DIR)shop1.webp" "$(FME_MF_DIR)place_of_worship.webp" "$(FME_MF_DIR)telephone.webp" "$(FME_MF_DIR)other.webp" "$(FME_MF_DIR)clothes.webp" "$(FME_MF_DIR)bench.webp" "$(FME_MF_DIR)bank.webp" "$(FME_MF_DIR)information.webp" "$(FME_MF_DIR)supermarket.webp" "$(FME_MF_DIR)accommodation.webp" "$(FME_MF_DIR)dentist.webp" "$(FME_MF_DIR)statue.webp" "$(FME_MF_DIR)school.webp" "$(FME_MF_DIR)sport.webp" "$(FME_MF_DIR)fast_food.webp" "$(FME_MF_DIR)toilets.webp" "$(FME_MF_DIR)bakery.webp" "$(FME_MF_DIR)ice_cream.webp" "$(FME_MF_DIR)bicycle.webp" "$(FME_MF_DIR)convenience.webp" "$(FME_MF_DIR)vending_machine.webp" "$(FME_MF_DIR)hospital.webp" "$(FME_MF_DIR)beauty.webp" "$(FME_MF_DIR)shop.webp" "$(FME_MF_DIR)clock.webp" "$(FME_MF_DIR)library.webp" "$(FME_MF_DIR)fountain.webp" "$(FME_MF_DIR)pub.webp""

Writers:
- FME_AR_2: FME_AR to GlobalAR.fmear

Note: Purpose & Objectives / This workspace generates an OpenStreetMap dataset based on the user's location in augmented reality using the FME Realize app. Each feature is transformed into a 3D geometry and styled depending on its feature type, and feature summary annotations are created for each feature. / The workspace searches for local landmarks in the immediate user vicinity and expands the search to a wider area if there are no landmarks around. The search radii for local and more remote landmarks can be adjusted in user parameters. / Key Transformers / AppearanceSetter : Sets appearance style(s) onto the sides of geometry surfaces representing OSM features / HTTPCaller : Makes POST requests to the OSM API to query data for the user's location / Rotator : Rotates features about a specified point in a counterclockwise direction to face the user in AR / Data Source(s) - Reader Feature Type / FeatureReader reads in OSM features from XML file retrieved from OSM API query / Data Output - Writer Feature Type / FeatureWriter writes the XML file returned from the OSM API request as an intermediate step before it is read in as XML / FME AR Writer saves the geometry in FMEAR format that is overlaid on a live view in AR / Customization / To customize this workspace, you can change the following: / Feature appearance (style, colour, texture) with the AppearanceSetter and AppearanceStyler transformers / Attributes to display in AR as summary annotations with the AttributeCreator transformers / Location that displayed OSM features are based on by following the instructions in the Preset Location Testing annotations / If you're recreating this workspace with your own data, it is recommended to build the workspace from scratch as your dataset will have different attributes and schema (structure). / For help with this workspace, please contact Safe Software Support and reference FME AR: OSM Anywhere.
Junction
    -> NeighborFinder [CANDIDATE]
    -> StatisticsCalculator
    -> NeighborFinder_2 [CANDIDATE]

Bookmark: Data and geometry preparation
Creator
    COORDSYS = LL84
    GEOMTYPE = Geometry Object
    NUM = 1
    CREATED -> AttributeCreator_2
Note: Get user location for anchor
Note: { "coordinates": [-123.1195,49.2833],"type": "Point"}
AttributeCreator_2
    ATTR_TABLE = SET_TO _location (varchar(200)) = $(LOCATION)
    -> JSONExtractor
Note: Reproject to AZMED_NEIGHBORHOOD
Reprojector_4
    DEST = _AZMED_NEIGHBORHOOD_
    INTERPOLATION_TYPE = NearestNeighbor
    RASTER_CELL_SIZE = PreserveCells
    RASTER_TOLERANCE = 0.0
    REPROJECTED -> Bufferer
    REPROJECTED -> AttributeCreator_4
    REPROJECTED -> Junction
Note: Create an OSM Overpass QL statement for extracting data from OSM
Note: Save and read OSM XML right away - that's the way to output data for further processing
AttributeCreator
    ATTR_TABLE:
      SET_TO _overpass_query (varchar(200)) = [out:xml];
        (
          node["building"](around:$(SEARCHRADIUS),@Value(fmear_anchor_latitude),@Value(fmear_anchor_longitude));  // Buildings
            way["building"](around:$(SEARCHRADIUS),@Value(fmear_anchor_latitude),@Value(fmear_anchor_longitude));  // Buildings
          node["amenity"](around:$(SEARCHRADIUS),@Value(fmear_anchor_latitude),@Value(fmear_anchor_longitude));  // Points of interest
          node["tourism"](around:$(SEARCHRADIUS),@Value(fmear_anchor_latitude),@Value(fmear_anchor_longitude));  // Touristic attractions
          node["historic"](around:$(SEARCHRADIUS),@Value(fmear_anchor_latitude),@Value(fmear_anchor_longitude));  // Historic attractions
          node["leasure"](around:$(SEARCHRADIUS),@Value(fmear_anchor_latitude),@Value(fmear_anchor_longitude));  //  Leasure
          node["shop"](around:$(SEARCHRADIUS),@Value(fmear_anchor_latitude),@Value(fmear_anchor_longitude));  // Shop
          node["sport"](around:$(SEARCHRADIUS),@Value(fmear_anchor_latitude),@Value(fmear_anchor_longitude));  // Sport
          way["highway"~"primary|secondary|tertiary|residential"]["name"](around:$(SEARCHRADIUS),@Value(fmear_anchor_latitude),@Value(fmear_anchor_longitude));   // Streets
        );
        (._;>;);  // Include all the necessary geometries
        out body;
    -> HTTPCaller
Note: reproject from LL to / _AZMED_NEIGHBORHOOD_
Reprojector_2
    DEST = _AZMED_NEIGHBORHOOD_
    INTERPOLATION_TYPE = NearestNeighbor
    RASTER_CELL_SIZE = PreserveCells
    RASTER_TOLERANCE = 0.0
    REPROJECTED -> Clipper [CANDIDATE]
Note: Clip the OSM data to the circumscribed rectangle around the circle defined by search radius
Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_OUTSIDE
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> TestFilter_3
Note: Process polygons buildings with names, roads, and nodes separately
TestFilter_3
    DEFAULT_VALUE = OtherNodes
    PASSED_TEST_GROUP_OUTPUT = FIRST
    TEST_LIST:
      "BOOL_OP,AND,COMPOSITE_TEST,""""""1"""""",TEST_CLAUSE,TEST @Value(fme_feature_type) = highway",Roads,"BOOL_OP,OR,COMPOSITE_TEST,""""""1"""""",TEST_CLAUSE,TEST @Value(fme_feature_type) = unknown",Drop,"BOOL_OP,AND,COMPOSITE_TEST,""""""1 AND 2"""""",TEST_CLAUSE,TEST @Value(fme_feature_type) = building
      TEST name NOT_ATTRIBUTE_IS_MISSING """,Building,"BOOL_OP,AND,COMPOSITE_TEST,""""""1"""""",TEST_CLAUSE,TEST @Value(fme_feature_type) = building",BuildingNoName
    Roads -> GeometryFilter
    Building -> AttributeRenamer_3
    OtherNodes -> CenterPointReplacer
AttributeRenamer_3
    ATTR_TABLE = RENAME_SET_DEFAULT building > buildingType
    KEEP_RENAMED_ONLY = no
    MISSING_INPUT_ATTRS = REMOVE
    -> GeometryFilter_2
Note: Keep only areas
GeometryFilter_2
    FILTER_MODE = SIMPLE
    FILTER_MULTI = FILTER_TYPES]Point Area]FILTER_TYPES_Simple]Point Area
    FILTER_TYPES = Point Area
    FILTER_TYPES_Simple = Point Area
    Area -> CenterPointReplacer
Note: Preserve points as points, replace polygons with points
CenterPointReplacer
    POINTTYPE = CENTER
    POINT -> NeighborFinder_2 [BASE]
    POINT -> StatisticsCalculator
Note: Find angles towards the anchor to rotate the features so that they face the observer
NeighborFinder_2
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Lines
    MATCHED -> CoordinateExtractor
Note: Preserve coordinates of the points as attributes
CoordinateExtractor
    IND = 0
    RECURSIVE = No
    X_ATTR = _x
    Y_ATTR = _y
    Z_ATTR = _z
    MODE = Specify Coordinate
    -> AttributeCreator_3
Note: Prepare summary annotations and icons. Create cube geometry attribute
AttributeCreator_3
    ATTR_TABLE:
      SET_TO _feature_summary_wiki (varchar(200)) = FME_CONDITIONAL:DEFAULT_VALUE'_FME_NO_OP_'BOOL_OP;OR;COMPOSITE_TEST;1;TEST wikidata ATTRIBUTE_HAS_A_VALUE _FME_BLANK_STRING_'**Wiki:** https://www.wikidata.org/wiki/@Value(wikidata)'FME_NUM_CONDITIONS2___
      SET_TO _feature_summary_name (varchar(200)) = FME_CONDITIONAL:DEFAULT_VALUE'_FME_NO_OP_'BOOL_OP;OR;COMPOSITE_TEST;1;TEST name ATTRIBUTE_HAS_A_VALUE _FME_BLANK_STRING_'**Name:** @Value(name)'FME_NUM_CONDITIONS2___
      SET_TO _feature_summary_website (varchar(200)) = FME_CONDITIONAL:DEFAULT_VALUE'_FME_NO_OP_'BOOL_OP;OR;COMPOSITE_TEST;1;TEST website ATTRIBUTE_HAS_A_VALUE _FME_BLANK_STRING_'**Website:** @Value(website)'FME_NUM_CONDITIONS2___
      SET_TO _feature_summary_note (varchar(200)) = FME_CONDITIONAL:DEFAULT_VALUE'_FME_NO_OP_'BOOL_OP;OR;COMPOSITE_TEST;1;TEST note ATTRIBUTE_HAS_A_VALUE _FME_BLANK_STRING_'**Note:** @Value(note)'FME_NUM_CONDITIONS2___
      SET_TO fmear_feature_summary (varchar(200)) = **Type:** @Value(fme_feature_type) @Value(_feature_summary_name)
        **Keywords:** @Trim(@Value(amenity) @Value(buildingType) @Value(leisure) @Value(public_transport) @Value(sport) @Value(tourism) @Value(cuisine) @Value(historic) @Value(natural) @Value(artwork_type) @Value(brand) @Value(culture) @Value(food) @Value(information) @Value(operator) @Value(shop) @Value(vending))
        @Trim(@Value(_feature_summary_wiki))
        @Trim(@Value(_feature_summary_website))
        @Trim(@Value(_feature_summary_note))
      SET_TO _geometry (buffer) =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
      SET_TO _icon_name (varchar(200)) = FME_CONDITIONAL:DEFAULT_VALUE'other'BOOL_OP;AND;COMPOSITE_TEST;1 AND 2;TEST @Value(fme_feature_type) = amenity;TEST @Value(amenity) = parking_entrance'parking'BOOL_OP;AND;COMPOSITE_TEST;1 AND 2;TEST @Value(fme_feature_type) = amenity;CASE_INSENSITIVE_TEST @Value(amenity) BEGINS_WITH bicycle'bicycle'BOOL_OP;AND;COMPOSITE_TEST;1 AND 2;TEST @Value(fme_feature_type) = amenity;TEST @Value(amenity) IN bar,pub'pub'BOOL_OP;AND;COMPOSITE_TEST;1;TEST @Value(fme_feature_type) = amenity'@Value(amenity)'BOOL_OP;OR;COMPOSITE_TEST;1;TEST @Value(fme_feature_type) = historic'@Value(historic)'BOOL_OP;AND;COMPOSITE_TEST;1 AND 2 AND 3;TEST @Value(fme_feature_type) = tourism;TEST @Value(tourism) = artwork;TEST @Value(artwork_type) = sculpture'statue'BOOL_OP;COMPOSITE;COMPOSITE_TEST;( 1 OR 2 ) AND ( 3 OR 4 );TEST @Value(fme_feature_type) = amenity;TEST @Value(fme_feature_type) = building;TEST @Value(artwork_type) = sculpture;TEST @Value(artwork_type) = statue'statue'BOOL_OP;AND;COMPOSITE_TEST;1 AND 2 AND 3;TEST @Value(fme_feature_type) = tourism;TEST @Value(tourism) = artwork;TEST artwork_type NOT_ATTRIBUTE_IS_MISSING _FME_BLANK_STRING_'@Value(artwork_type)'BOOL_OP;AND;COMPOSITE_TEST;1 AND 2;TEST @Value(fme_feature_type) = tourism;TEST @Value(tourism) = artwork'statue'BOOL_OP;AND;COMPOSITE_TEST;1 AND 2;TEST @Value(fme_feature_type) = tourism;TEST @Value(tourism) = information'information'BOOL_OP;AND;COMPOSITE_TEST;1 AND 2;TEST @Value(fme_feature_type) = tourism;TEST @Value(tourism) = museum'museum'BOOL_OP;AND;COMPOSITE_TEST;1 AND 2;TEST @Value(fme_feature_type) = building;TEST @Value(tourism) = museum'museum'BOOL_OP;COMPOSITE;COMPOSITE_TEST;1 AND 2 OR 3;TEST @Value(fme_feature_type) = building;TEST @Value(landuse) = retail;TEST @Value(buildingType) = retail'shop'BOOL_OP;COMPOSITE;COMPOSITE_TEST;1 OR 2 AND 3;TEST @Value(fme_feature_type) = tourism;TEST @Value(fme_feature_type) = building;TEST @Value(tourism) IN hotel,hostel,guest_house,shelter'accommodation'BOOL_OP;AND;COMPOSITE_TEST;1 AND 2;TEST @Value(fme_feature_type) = shop;TEST @Value(shop) IN clothes,florist,beauty,bakery,convenience,deli,supermarket,gift'@Value(shop)'BOOL_OP;AND;COMPOSITE_TEST;1;TEST @Value(fme_feature_type) = shop'shop'FME_NUM_CONDITIONS17___
    -> Orientor
Orientor
    FLIP_APPEARANCES_LOOKUP = FLIP_APPEARANCES
    KIND = REVERSE
    FLIP_APPEARANCES_CHOICE = Yes
    ORIENTED -> GeometryReplacer_2
Note: Replace points with cube geometry at 0,0 (we will need to offset it later, this is why we extracted point coordinates earlier)
GeometryReplacer_2
    KIND = fmehex
    REMOVE_ATTRIBUTE = Yes
    SOURCE = @Value(_geometry)
    KIND_LONG = Hex Encoded FME Binary
    -> AppearanceSetter_2 [GEOMETRY]

Bookmark: Extract lat/lon from json and make a point
JSONExtractor
    EXTRACT_QUERY_TABLE = fmear_anchor_latitude json["coordinates"][1] fmear_anchor_longitude json["coordinates"][0]
    JSON_DOCUMENT = @Value(_location)
    READ_FROM_FILE = NO
    EVALUATED -> VertexCreator
VertexCreator
    MEASURE_TYPE_LOOKUP = CONTINUOUS
    MODE = REPLACE
    REMOVE_ATTRIBUTES = No
    XVAL = @Value(fmear_anchor_longitude)
    YVAL = @Value(fmear_anchor_latitude)
    MEASURE_TYPE = Continuous
    MODE_NAME = Replace with Point
    -> AttributeCreator
    -> Reprojector_4

Bookmark: Defining the placement of the model
Note: Create an anchor object
AttributeCreator_4
    ATTR_TABLE = SET_TO fmear_location_feature (varchar(200)) = anchor
    -> CoordinateSystemRemover
CoordinateSystemRemover
    -> AttributeRemover_2
AttributeRemover_2
    REMOVE_ATTRS = fmear_anchor_latitude,fmear_anchor_longitude
    -> Anchor (writer FME_AR_2)
Note: There will be no Anchor features created in FMEAR file. Instead this point will be stored in the header of the output AR file and used for a correct placement of the model around the observer. This feature can go to any other feature type.
Anchor (writer FME_AR_2)

Bookmark: Make a square with the side = 2 search radii
Bufferer
    ANGLE = 22.5
    CAP_STYLE_LOOKUP = CAP_ARC
    CORNER_STYLE_LOOKUP = JOIN_ARC
    MODE = AREA
    OFFSET = $(SEARCHRADIUS)
    OFFSET_UNITS = NONE
    PRECISION = APPROX
    CAP_STYLE = Arc
    CORNER_STYLE = Arc
    BUFFERED -> BoundingBoxReplacer
BoundingBoxReplacer
    BBTYPE = BB
    BOXTYPE = 2D Bounding Box
    BOX -> Clipper [CLIPPER]

Bookmark: Save and read OSM XML right away - that's the way to output data for further processing
Note: Send the request with the query to the OSM API
HTTPCaller
    CLIENT_CERTIFICATE_TYPE = NONE
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = text_line_data
    TARGET_ATTR_ENCODING = auto-detect
    TARGET_URL = https://overpass-api.de/api/interpreter
    TRANSFER_TIMEOUT_LENGTH = 90
    UPLOAD_BODY = @Value(_overpass_query)
    UPLOAD_TYPE = STRING_UPLOAD
    USE_COOKIES = No
    VERIFY_SSL_CERTIFICATES = Yes
    UPLOAD_CONTENT_TYPE = Text (text/plain)
    -> TempPathnameCreator
Note: Reserve a path to save the results of the query as OSM XML
TempPathnameCreator
    BASENAME = osm
    EXTENSION = osm
    PATHNAME_ATTR = _pathname
    -> FeatureWriter [text_line]
Note: Save the XML just like a text file
FeatureWriter
    DATASET = @Value(_pathname)
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = application/xml
    TEXTLINE_OVERWRITE_FILE = YES
    TEXTLINE_WRITE_LAST_EOL = YES
    TEXTLINE_WRITE_UTF8_BOM = YES
    TOTAL_FEATURES_WRITTEN_ATTR = _total_features_written
    text_line -> AttributeRemover
Note: Some cleaning for easier attribute manipulation
AttributeRemover
    REMOVE_ATTRS = _http_status_code,_overpass_query,text_line_data,_creation_instance,_location,fmear_anchor_latitude,fmear_anchor_longitude
    -> FeatureReader_3 [INITIATOR]
Note: Read the OSM XML with the OSM reader
FeatureReader_3
    ATTRS_TO_EXPOSE = fme_feature_type amenity artwork_type brand building cuisine culture food historic information landuse leisure name natural note operator public_transport shop sport tourism vending website wikidata
    ATTR_ACCUM_MODE = Merge Initiator and Result
    ATTR_CONFLICT_RES = Use Result
    ATTR_IGNORE_NULLS = No
    CLIP_TO_ENVELOPE = NO
    COMBINE_GEOM = Use Result
    DATASET = @Value(_pathname)
    FORMAT = OSM
    INITIATOR_FIRST_OUTPUT = default
    INTERACT = NONE
    ORDER_RESULTS = No
    OSM_ALLOW_DUPLICATE_COORDINATES = yes
    OSM_BUILD_MULTIPOLYGON_RELATION = yes
    OSM_CACHE_WAYS_AND_RELATIONS = no
    OSM_COMMUNITY_FEATURE_TYPES = MAPPED
    OSM_HANDLE_MULTI = SELECT_FIRST
    OSM_OUTPUT_INCOMPLETE_WAYS_AND_RELATIONS = yes
    OSM_REMOVE_NODE_LIST = no
    OSM_SCAN_ALL_FEATURES_FOR_SCHEMA = yes
    OSM_USER_CONFIG = NO
    OUTPUT_ADD_SCHEMA_ATTRIBUTES = NO
    OUTPUT_FEATURES_DISPLAY = Schema and Data Features
    <OTHER> -> Reprojector_2
    <REJECTED> -> FeatureReader__Rejected_
FeatureReader__Rejected_: Logger
    LOG_FEATURE = LOG_ONLY
    MAXCOORDS = 20
    MAXFEATS = 20
    MESSAGE = OSM data reading error
    SEVERITY = ERROR

Bookmark: Determing which landmarks will be shown to the user, and creating their feature summaries
Note: Calculate how many local landmarks we have.
StatisticsCalculator
    ATTR_ACCUM_MODE = None
    CALCULATION_MODE = NUMERIC
    FEAT_STATS = _creation_instance,NUMERIC_MODE,,,COUNT,,,,,,,,,,
    COMPLETE -> Tester_3
Note: If we have too few local landmarks, we will generate a few landmarks within 10 km radius
Tester_3
    BOOL_OP = COMPOSITE
    COMPOSITE_TEST = 1 AND 2
    TEST_CLAUSE:
      TEST @Value(_creation_instance.total_count) < $(LOCALLANDMARKTHRESHOLD)
      TEST fmear_anchor_latitude NOT_ATTRIBUTE_IS_MISSING ""
    TEST_MODE = TEST
    PASSED -> AttributeCreator_6
Note: Create OSM Overpass query
Note: Save and read OSM XML right away - that's the way to output data for further processing
AttributeCreator_6
    ATTR_TABLE:
      SET_TO _overpassExpanded_query (varchar(200)) = [out:xml];
        (
          node["natural"="peak"](around:$(EXPANDEDSEARCHRADIUS),@Value(fmear_anchor_latitude),@Value(fmear_anchor_longitude));  // Mountains/peaks
          node["aeroway"="aerodrome"](around:$(EXPANDEDSEARCHRADIUS),@Value(fmear_anchor_latitude),@Value(fmear_anchor_longitude));  // Airports
          node["tourism"="attraction"](around:$(EXPANDEDSEARCHRADIUS),@Value(fmear_anchor_latitude),@Value(fmear_anchor_longitude));  // Tourist attractions
          node["historic"="monument"](around:$(EXPANDEDSEARCHRADIUS),@Value(fmear_anchor_latitude),@Value(fmear_anchor_longitude));  // Historic monuments
          // Add more landmark types as necessary
        );
        out body;
    -> HTTPCaller_2
Note: Keep to more than 25 landmarks within 10 km radius
Sampler_2
    MODE = RANDOM
    RATE = 25
    SAMPLE_TYPE_MULTIPLIER = -1
    SAMPLE_MODE = Yes
    SAMPLE_TYPE_LONG = First N Features
    SAMPLED -> Reprojector_3
Reprojector_3
    DEST = _AZMED_NEIGHBORHOOD_
    INTERPOLATION_TYPE = NearestNeighbor
    RASTER_CELL_SIZE = PreserveCells
    RASTER_TOLERANCE = 0.0
    REPROJECTED -> NeighborFinder [BASE]
Note: Calculate the angle from the object to anchor
NeighborFinder
    ATTR_ACCUM_MODE = Merge Candidate
    ATTR_CONFLICT_RES = Use Base
    CANDIDATES_FIRST = No
    INSERT_VERTEX = No
    MEASURES_FROM_CANDIDATE = Yes
    MEASURE_TYPE = Continuous
    MODE = Bases and Candidates
    TREAT_POLYGON_AS = Lines
    MATCHED -> VertexCreator_2
Note: Create a point at the anchor (observer location)
VertexCreator_2
    MEASURE_TYPE_LOOKUP = CONTINUOUS
    MODE = REPLACE
    REMOVE_ATTRIBUTES = No
    XVAL = @Value(_closest_candidate_x)
    YVAL = @Value(_closest_candidate_y)
    MEASURE_TYPE = Continuous
    MODE_NAME = Replace with Point
    -> AttributeCreator_5
Note: Create feature summaries
AttributeCreator_5
    ATTR_TABLE:
      SET_TO _feature_summary_note (varchar(200)) = FME_CONDITIONAL:DEFAULT_VALUE'_FME_NO_OP_'BOOL_OP;OR;COMPOSITE_TEST;1;TEST note ATTRIBUTE_HAS_A_VALUE _FME_BLANK_STRING_'**Note:** @Value(note)'FME_NUM_CONDITIONS2___
      SET_TO _feature_summary_name (varchar(200)) = FME_CONDITIONAL:DEFAULT_VALUE'_FME_NO_OP_'BOOL_OP;OR;COMPOSITE_TEST;1;TEST name ATTRIBUTE_HAS_A_VALUE _FME_BLANK_STRING_'**Name:** @Value(name)'FME_NUM_CONDITIONS2___
      SET_TO fmear_feature_summary (varchar(200)) = @Value(_feature_summary_name)
        **Distance:** @round(@Evaluate(@Value(_distance)/1000),1)km
        **Keywords:** @Trim(@Value(amenity) @Value(tourism) @Value(cuisine) @Value(historic) @Value(natural) @Value(artwork_type) @Value(brand) @Value(culture) @Value(information) @Value(operator) @Value(shop) @Value(vending))
        @Value(_feature_summary_note)
    -> 3DArrowReplacer [Point]
Note: Replace landmarks with arrows pointing towards them
3DArrowReplacer
    XSCALE = 1
    _ANGLE = @Value(_angle)
    _CLOSEST_BASE_X = @Value(_closest_base_x)
    _CLOSEST_BASE_Y = @Value(_closest_base_y)
    _CLOSEST_CANDIDATE_X = @Value(_closest_candidate_x)
    _CLOSEST_CANDIDATE_Y = @Value(_closest_candidate_y)
    3DArrow -> CoordinateSystemRemover_2

Bookmark: Save and read OSM XML right away - that's the way to output data for further processing
Note: Send the request to the OSM API
HTTPCaller_2
    CLIENT_CERTIFICATE_TYPE = NONE
    CONNECTION_TIMEOUT_LENGTH = 60
    CONTENT_TYPE_LOOKUP = text/plain
    ERROR_ATTR = _error
    FOLLOW_REDIRECTS = FOLLOW_WITH_GET
    HTTP_METHOD = POST
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://overpass-api.de/api/interpreter
    TRANSFER_TIMEOUT_LENGTH = 90
    UPLOAD_BODY = @Value(_overpassExpanded_query)
    UPLOAD_TYPE = STRING_UPLOAD
    USE_COOKIES = No
    VERIFY_SSL_CERTIFICATES = Yes
    UPLOAD_CONTENT_TYPE = Text (text/plain)
    -> AttributeRenamer_2
    <REJECTED> -> HTTPCaller_2__Rejected_
AttributeRenamer_2
    ATTR_TABLE = RENAME_SET_DEFAULT _response_body > text_line_data
    KEEP_RENAMED_ONLY = no
    MISSING_INPUT_ATTRS = REMOVE
    -> TempPathnameCreator_2
Note: Reserve a path to save OSM XML
TempPathnameCreator_2
    BASENAME = osm
    EXTENSION = osm
    PATHNAME_ATTR = _pathname
    -> FeatureWriter_2 [text_line]
Note: Save OSM XML as text
FeatureWriter_2
    DATASET = @Value(_pathname)
    DATASET_ATTR = _dataset
    FEATURE_TYPE_LIST_ATTR = _feature_types
    FORMAT = TEXTLINE
    TEXTLINE_COORDINATE_SYSTEM_GRANULARITY = FEATURE
    TEXTLINE_DESTINATION_DATASETTYPE_VALIDATION = Yes
    TEXTLINE_ENCODING = UTF-8
    TEXTLINE_END_OF_LINE = System
    TEXTLINE_MIME_TYPE = application/xml
    TEXTLINE_OVERWRITE_FILE = YES
    TEXTLINE_WRITE_LAST_EOL = YES
    TEXTLINE_WRITE_UTF8_BOM = YES
    TOTAL_FEATURES_WRITTEN_ATTR = _total_features_written
    text_line -> FeatureReader_2 [INITIATOR]
Note: Read OSM data as XML
FeatureReader_2
    ATTRS_TO_EXPOSE = fme_feature_type name amenity note cuisine tourism natural historic building wikidata culture artwork_type information vending operator shop brand website
    ATTR_ACCUM_MODE = Only Use Result
    CLIP_TO_ENVELOPE = NO
    COMBINE_GEOM = Use Result
    DATASET = @Value(_pathname)
    FORMAT = OSM
    INITIATOR_FIRST_OUTPUT = default
    INTERACT = NONE
    ORDER_RESULTS = No
    OSM_ALLOW_DUPLICATE_COORDINATES = yes
    OSM_BUILD_MULTIPOLYGON_RELATION = yes
    OSM_CACHE_WAYS_AND_RELATIONS = no
    OSM_COMMUNITY_FEATURE_TYPES = MAPPED
    OSM_HANDLE_MULTI = SELECT_FIRST
    OSM_OUTPUT_INCOMPLETE_WAYS_AND_RELATIONS = yes
    OSM_REMOVE_NODE_LIST = no
    OSM_SCAN_ALL_FEATURES_FOR_SCHEMA = yes
    OSM_USER_CONFIG = NO
    OUTPUT_ADD_SCHEMA_ATTRIBUTES = NO
    OUTPUT_FEATURES_DISPLAY = Schema and Data Features
    <OTHER> -> Sampler_2
    <REJECTED> -> FeatureReader_2__Rejected_
FeatureReader_2__Rejected_: Logger
    LOG_FEATURE = LOG_ONLY
    MAXCOORDS = 20
    MAXFEATS = 20
    MESSAGE = OSM data reading error
    SEVERITY = ERROR
HTTPCaller_2__Rejected_: Logger
    LOG_FEATURE = LOG_ONLY
    MAXCOORDS = 20
    MAXFEATS = 20
    MESSAGE = Request to OSM failed
    SEVERITY = ERROR

Bookmark: Remove coordinate system
CoordinateSystemRemover_2
    -> HorizonLandmarks (writer FME_AR_2)
CoordinateSystemRemover_4
    -> StreetLabels (writer FME_AR_2)
Note: If a user adjusts location manually, it will work for any place they choose
CoordinateSystemRemover_3
    -> LocalLandmarks (writer FME_AR_2)

Bookmark: Write data to FME AR
Note: Save local landmark icon cubes as FMEAR Asset
HorizonLandmarks (writer FME_AR_2)
    attributes: name text
Note: Save street labels as FME AR Asset
StreetLabels (writer FME_AR_2)
    attributes: name text, status text, maxspeed text, lanes integer
Note: Save local landmark icon cubes as FMEAR Asset
LocalLandmarks (writer FME_AR_2)

Bookmark: Creating and populating the labels for nearby streets
Note: Keep only lines (road centerlines)
GeometryFilter
    FILTER_MODE = SIMPLE
    FILTER_MULTI = FILTER_TYPES]Line]FILTER_TYPES_Simple]Line
    FILTER_TYPES = Line
    FILTER_TYPES_Simple = Line
    Curve -> AttributeExposer_2
Note: Make sure the necessary attributes are exposed
Note: Creating and populating the labels for nearby streets
AttributeExposer_2
    ATTR_TABLE = name,,highway,,maxspeed,,lanes,
    -> StringLengthCalculator
Note: Prepare attributes for the writer
AttributeManager
    ATTR_TABLE:
      REMOVE _pathname (buffer)
      REMOVE fme_feature_type (buffer)
      RENAME_SET_VALUE highway > status (varchar(200))
      REMOVE _road_name_length (uint64)
      REMOVE _length (real64)
      REMOVE acAngle (buffer)
      SET_TO fmear_feature_summary (varchar(200)) = **Name:** @Value(name)
        **Status:** @Value(status)
        **Number of Lanes:** @Value(lanes)
        **Max Speed:** @Value(maxspeed)
      REMOVE amenity (buffer)
      REMOVE note (buffer)
      REMOVE cuisine (buffer)
      REMOVE tourism (buffer)
      REMOVE natural (buffer)
      REMOVE historic (buffer)
      REMOVE building (buffer)
      REMOVE wikidata (buffer)
      REMOVE culture (buffer)
      REMOVE artwork_type (buffer)
      REMOVE information (buffer)
      REMOVE vending (buffer)
      REMOVE operator (buffer)
      REMOVE shop (buffer)
      REMOVE brand (buffer)
      REMOVE website (buffer)
      REMOVE leisure (buffer)
      REMOVE sport (buffer)
      REMOVE public_transport (buffer)
    USER_EXPOSED_ATTRIBUTES = fmear_feature_summary,fmear_location_feature,_http_status_code,text_line_data,_overpass_query
    -> CoordinateSystemRemover_4

Bookmark: Street labels
StringLengthCalculator
    LENGTH_ATTR = _road_name_length
    SRC_ATTR = name
    -> Generalizer
Generalizer
    ALG = Douglas
    PRESERVE = No
    PRESERVE_PATHS_LOOKUP = NO
    TOLERANCE = 10
    ALG_TEXT = Douglas (Generalize)
    PRESERVE_PATHS = No
    -> Chopper
Chopper
    APPROX_LENGTH = @Length()/2
    DEAGGREGATE_INPUT = Deaggregate
    GRID_AREAS = Yes
    MODE_LOOKUP = LENGTH
    MODE = By Length
    CHOPPED -> LengthCalculator
    UNTOUCHED -> LengthCalculator
    <REJECTED> -> Chopper__Rejected_
LengthCalculator
    DIM = 2
    LEN_ATTR = _length
    MULT = 1
    -> Tester
Tester
    BOOL_OP = OR
    TEST_CLAUSE = TEST @Value(_length) > 25
    TEST_MODE = TEST
    PASSED -> AzimuthCalculator [LINE]
AzimuthCalculator
    Angle -> CenterPointExtractor_2
CenterPointExtractor_2
    CENTX = _inside_x
    CENTY = _inside_y
    CENTZ = _inside_z
    EXTRACTIONMODE = CENTER
    -> 2DBoxReplacer
2DBoxReplacer
    MAXXVALATTR = @Value(_inside_x)+@Value(_road_name_length)/2
    MAXYVALATTR = @Value(_inside_y)+2
    MINXVALATTR = @Value(_inside_x)-@Value(_road_name_length)/2
    MINYVALATTR = @Value(_inside_y)
    BOX -> Counter_2
Counter_2
    CNT_ATTR = _label_count
    SCOPE = Local
    START = 0
    -> MapnikRasterizer [Label]
    -> 3DRotator_4
MapnikRasterizer
    BACKGROUND_COLOR = 1,1,1
    BACKGROUND_COLOR_ALPHA = 1
    COLROW_OR_SPACING = CellSize
    GROUP_BY = _label_count name
    INTERPRETATION_TYPE = RGB24
    LAYER_CARDINALITY_LOOKUP = RULES
    MAPNIK_CONFIG = Label;polygon;"__ignore__color-group;;fill;0.262745,0.47451,0.247059;fill-opacity;1;__ignore__smoothing-group;;gamma;1;gamma-method;power;smooth;0;__ignore__comp-group;;comp-op;src-over;FME_CONTROLLER_QUERY_FILE;plugins/mapnik/polygon.fme;FME_CONTROLLER_CHOICE;polygon";Label;line;"__ignore__color-group;;stroke;1,1,1;stroke-opacity;1;__ignore__line-style-group;;stroke-width;2;stroke-linejoin;round;stroke-linecap;butt;stroke-dasharray;;stroke-miterlimit;4;__ignore__positioning-group;FME_DISCLOSURE_OPEN;offset;-3;__ignore__smoothing-group;FME_DISCLOSURE_OPEN;stroke-gamma;1;stroke-gamma-method;power;smooth;0;rasterizer;full;__ignore__comp-group;;comp-op;src-over;FME_CONTROLLER_QUERY_FILE;plugins/mapnik/line.fme;FME_CONTROLLER_CHOICE;line";Label;text;"__ignore__text-properties-group;FME_DISCLOSURE_OPEN;name;name;face-name;Tahoma,Normal;size;28;__ignore__color-group;;fill;1,1,1;opacity;1;halo-fill;1,1,1;halo-radius;0;__ignore__positioning-group;FME_DISCLOSURE_OPEN;text-ratio;0;wrap-width;0;wrap-before;No;spacing;0;character-spacing;0;line-spacing;0;label-position-tolerance;0;dx;0;dy;8;avoid-edges;No;minimum-distance;0;minimum-padding;0;minimum-path-length;0;allow-overlap;No;orientation;0;placement;interior;placement-type;simple;placements;X,24,22,20,18;max-char-angle-delta;22.5;horizontal-alignment;auto;justify-alignment;auto;vertical-alignment;top;__ignore__comp-group;;comp-op;src-over;FME_CONTROLLER_QUERY_FILE;plugins/mapnik/text.fme;FME_CONTROLLER_CHOICE;text"
    SPACING = 0.05
    SPECIFY_GROUND_EXTENTS = Use input data ground extents
    INTERPRETATION_TYPE_LOOKUP = RGB24
    LAYER_CARDINALITY = Each rendering rule is a layer
    RASTER -> AppearanceStyler
AppearanceStyler
    ALPHA = 1.0
    APPEARANCE_NAME = @Value(name)
    DIFFUSE_COLOR = 1,1,1
    SHININESS = 0.1
    SPECULAR_COLOR = 0.160784,0.160784,0.160784
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP = REPEAT_BOTH
    TEXTURE_WRAP_DISPLAY = Repeat in U and V
    -> AppearanceSetter_7 [APPEARANCE]
3DRotator_4
    ANGLE = 90
    AXIS_CHOICE_LOOKUP = CUSTOM
    XDIR = 1
    XORIG = @Value(_inside_x)
    YDIR = 0
    YORIG = @Value(_inside_y)
    ZDIR = 0
    ZORIG = 0
    AXIS_CHOICE = Custom Axis
    ROTATED -> Rotator_2
Rotator_2
    ANGLE = @Value(acAngle)
    XORIG = @Value(_inside_x)
    YORIG = @Value(_inside_y)
    ROTATED -> FaceReplacer
FaceReplacer
    ANGULAR_TOLERANCE_CHOICE_LOOKUP = AUTO
    THICKNESS_TOLERANCE_CHOICE_LOOKUP = AUTO
    ANGULAR_TOLERANCE_CHOICE = Automatic
    THICKNESS_TOLERANCE_CHOICE = Automatic
    -> AppearanceSetter_7 [GEOMETRY]
AppearanceSetter_7
    APPEARANCE_DEFINITION_STORAGE = CREATE
    APPEARANCE_NAME = @Value(name)
    GQUERY:
      for $geom in //geometry
      where $geom/count(parent::geometry) = 0
      return number($geom/@fme_id)
    GROUP_BY = name
    SIDE_OPTION = FRONT
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front Side
    TEXTURE_MAPPING_TYPE_CHOICE = Surface Normal
    USE_EXISTING_TEXTURE_COORDINATES = No
    -> Offsetter_3
    -> Rotator
    <REJECTED> -> AppearanceSetter_7__Rejected_
Rotator
    ANGLE = 180
    XORIG = @Value(_inside_x)
    YORIG = @Value(_inside_y)
    ROTATED -> Offsetter
Offsetter
    AZIMUTH_2D = @Value(acAngle)+90
    MODE_LOOKUP = POLAR
    RADIUS_2D = -0.01
    MODE = Polar Coordinate
    OFFSET -> Offsetter_3
Offsetter_3
    MODE_LOOKUP = CARTESIAN
    XOFF = 0
    YOFF = 0
    ZOFF = 3
    MODE = Cartesian Coordinate
    OFFSET -> AttributeManager
AppearanceSetter_7__Rejected_: Logger
    LOG_FEATURE = LOG_ONLY
    MAXCOORDS = 20
    MAXFEATS = 20
    MESSAGE = Feature is:
    SEVERITY = INFO
Chopper__Rejected_: Logger
    LOG_FEATURE = LOG_ONLY
    MAXCOORDS = 20
    MAXFEATS = 20
    MESSAGE = Feature is:
    SEVERITY = INFO

Bookmark: Creating and setting the appearance of the icons for landmarks
Note: Read icons for local landmarks
WEBP (reader WEBP_1)
    -> AttributeRenamer_4
AttributeRenamer_4
    ATTR_TABLE = RENAME_SET_DEFAULT fme_basename > _icon_name
    KEEP_RENAMED_ONLY = no
    MISSING_INPUT_ATTRS = REMOVE
    -> Tester_2
Note: Separate icons for particular landmarks from the one used for everything else
Tester_2
    BOOL_OP = OR
    TEST_CLAUSE = TEST @Value(_icon_name) = other
    TEST_MODE = TEST
    PASSED -> AppearanceSetter_4 [APPEARANCE]
    FAILED -> AppearanceSetter_2 [APPEARANCE]
Note: Set appearances on cubes, for which specific icons were created
AppearanceSetter_2
    APPEARANCE_DEFINITION_STORAGE = CREATE
    APPEARANCE_NAME = @Value(_icon_name)
    GQUERY:
      for $geom in //geometry
      where <fme-in-operation>fme:trait-equals(fme:get-trait($geom, '_count'), '1')
      or fme:trait-equals(fme:get-trait($geom, '_count'), '2')
      or fme:trait-equals(fme:get-trait($geom, '_count'), '3')
      or fme:trait-equals(fme:get-trait($geom, '_count'), '4')</fme-in-operation>
      return number($geom/@fme_id)
    GROUP_BY = _icon_name
    SHININESS = 0
    SIDE_OPTION = FRONT
    SPECULAR_COLOR = 0,0,0
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front Side
    TEXTURE_MAPPING_TYPE_CHOICE = Surface Normal
    USE_EXISTING_TEXTURE_COORDINATES = No
    -> AppearanceSetter_4 [GEOMETRY]
Note: Set a question mark appearance on all cubes with no specific icon
AppearanceSetter_4
    APPEARANCE_DEFINITION_STORAGE = CREATE
    APPEARANCE_NAME = Other
    GQUERY:
      for $geom in //geometry
      where not(fme:appearance-front($geom)/@has_texture = xs:boolean('true'))
      return number($geom/@fme_id)
    SHININESS = 0
    SIDE_OPTION = FRONT
    SPECULAR_COLOR = 0,0,0
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front Side
    TEXTURE_MAPPING_TYPE_CHOICE = Surface Normal
    USE_EXISTING_TEXTURE_COORDINATES = No
    -> AppearanceSetter_3 [GEOMETRY]
Note: Make transparent top and bottom of the cube
AppearanceSetter_3
    ALPHA = 0
    APPEARANCE_DEFINITION_STORAGE = CREATE
    APPEARANCE_NAME = TopBottom
    GQUERY:
      for $geom in //geometry
      where <fme-in-operation>fme:trait-equals(fme:get-trait($geom, '_count'), '0')
      or fme:trait-equals(fme:get-trait($geom, '_count'), '5')</fme-in-operation>
      return number($geom/@fme_id)
    SIDE_OPTION = BOTH
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> Scaler
Note: Adjust the cube size if needed
Scaler
    DISABLE_FACTORIES = *
    RASTER_SCALING = Extents
    TEXT_LOC_ONLY = Location and Size
    XSCALE = 2
    YSCALE = 2
    ZSCALE = 2
    SCALE_ORIGIN = Center Point
    SCALED -> Offsetter_6
Note: Offset to the original point position in local CS
Offsetter_6
    MODE_LOOKUP = CARTESIAN
    XOFF = @Value(_x)
    YOFF = @Value(_y)
    ZOFF = 1.5
    MODE = Cartesian Coordinate
    OFFSET -> Rotator_4
Note: Rotate cube to face the observer standing at the anchor point
Rotator_4
    ANGLE = @Value(_angle)+45
    XORIG = @Value(_x)
    YORIG = @Value(_y)
    ROTATED -> CoordinateSystemRemover_3

Bookmark: Running the Workspace - Step-by-step
Note: Step 1: / Change the feature summaries and appearance styling for the different infrastructure features (optional).
Note: Step 2: / Publish the workspace to FME Flow.
Note: Step 3: / On FME Flow, create an Flow AR App with this workspace. You can either hide or expose the "Auto Populate Geolocation" parameter to the FME AR app users in the "Hide Parameter in App".
Note: Step 4: / Open the FME Realize app on an iOS device. Connect to your FME Flow.
Note: Step 5: / Run the AR app created in Step 3 and visualize the data in augented reality. Adjust model rotation if necessary.

Bookmark: Scenario
Note: The user will see a scene with OSM features based on the on their location, or the preset location coordinates entered when running the AR App.
Note: The workspace can be altered to use different symbology and summary annotations for different landmark features from OSM.
Note: OSM data is extracted using the OSM API and read in as an XML file. Collapsed bookmarks throughout the workspace contain this process. Custom transformers are also used in the workspace to calculate azimuth (AzimuthCalculator) and identify landmarks with arrows pointing to them (3DArrowReplacer).

FME custom transformer AzimuthCalculator
Calculates the angle and the  azimuth of a line or a polyline.
For polylines it returns the average angle and azimuth. 
The resultant lines have two new attributes - acAngle and acAzimuth.
For getting information about each segment of the polyline use PolylineAnalyzer.

LINE (input)
    -> COORDINATEFETCHER
COORDINATEFETCHER: CoordinateExtractor
    IND = 0
    RECURSIVE = No
    X_ATTR = acX1
    Y_ATTR = acY1
    Z_ATTR = acZ1
    Z_DEFAULT = -9999
    MODE = Specify Coordinate
    -> COORDINATEFETCHER_2
COORDINATEFETCHER_2: CoordinateExtractor
    IND = -1
    RECURSIVE = No
    X_ATTR = acX2
    Y_ATTR = acY2
    Z_ATTR = acZ2
    Z_DEFAULT = -9999
    MODE = Specify Coordinate
    -> EXPRESSIONEVALUATOR_2
EXPRESSIONEVALUATOR_2: ExpressionEvaluator
    ACTION = Create New Attribute
    EXPRESSION = @acos((@Value(acX2)-@Value(acX1))/@sqrt(@pow((@Value(acY2)-@Value(acY1)),2) + @pow((@Value(acX2)-@Value(acX1)),2)))* (180/3.14159265)
    VAL_ATTR = acAngle
    -> EXPRESSIONEVALUATOR_6
EXPRESSIONEVALUATOR_6: ExpressionEvaluator
    ACTION = Create New Attribute
    EXPRESSION = ((@Value(acY2)-@Value(acY1))<0)?(360-@Value(acAngle)):(@Value(acAngle))
    VAL_ATTR = acAngle
    -> AttributeRemover
AttributeRemover
    REMOVE_ATTRS = acX1,acY2,acZ1,acZ2,acY1,acX2
    -> Angle (output)
Angle (output)

FME custom transformer 3DArrowReplacer

Parameters:
- XSCALE = 1   # X Scale Factor
- _ANGLE = @Value(_angle)   # Angle
- _CLOSEST_CANDIDATE_X = @Value(_closest_candidate_x)   # Closest Candidate X
- _CLOSEST_CANDIDATE_Y = @Value(_closest_candidate_y)   # Closest Candidate Y
- _CLOSEST_BASE_X = @Value(_closest_base_x)   # Closest Base X
- _CLOSEST_BASE_Y = @Value(_closest_base_y)   # Closest Base Y

Point (input)
    -> AttributeCreator_5
Note: Create arrow geometry attribute
AttributeCreator_5
    ATTR_TABLE = SET_TO _geometry5 (buffer) =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
    -> GeometryReplacer
Note: Replace point with arrow geometry
GeometryReplacer
    KIND = fmehex
    REMOVE_ATTRIBUTE = Yes
    SOURCE = @Value(_geometry5)
    KIND_LONG = Hex Encoded FME Binary
    -> AppearanceSetter_4 [GEOMETRY]
Note: Make the arrow longer (or narrower)
Scaler
    DISABLE_FACTORIES = *
    RASTER_SCALING = Extents
    TEXT_LOC_ONLY = Location and Size
    XSCALE = $(XSCALE)
    YSCALE = $(XSCALE)*2
    ZSCALE = $(XSCALE)
    SCALE_ORIGIN = Center Point
    SCALED -> Rotator_3
Note: Rotate away from observer towards landmarks
Rotator_3
    ANGLE = @Value(_angle)+90
    XORIG = 0
    YORIG = 0
    ROTATED -> Extruder
Note: Slightly extrude (to increase the (true) feeling that the arrow is not looking up, but rather away
Extruder
    DIRECTION_LOOKUP = AUTO
    DISTANCE = 0.25
    DIRECTION = Auto
    EXTRUDED -> Sorter
Note: Sort by angle
Sorter
    SORT_PARM = _angle NUMERIC ASCENDING
    SORTED -> Counter_2
Note: assign count attribute
Counter_2
    CNT_ATTR = _count
    DOMAIN = counter
    SCOPE = Global
    START = 0
    -> Offsetter
Note: place the arrows at slightly different elevation (1 mm difference) to avoid flickering from overlapping arrows
Offsetter
    MODE_LOOKUP = CARTESIAN
    XOFF = @Value(_closest_candidate_x)
    YOFF = @Value(_closest_candidate_y)
    ZOFF = 0.001*@Value(_count)-2
    MODE = Cartesian Coordinate
    OFFSET -> Offsetter_4
Note: offset away from the observer towards the landmark
Offsetter_4
    AZIMUTH_2D = @Value(_angle)-180
    MODE_LOOKUP = POLAR
    RADIUS_2D = 30
    MODE = Polar Coordinate
    OFFSET -> 3DArrow (output)
3DArrow (output)

Bookmark: Set arrow colors
AppearanceSetter_4
    AMBIENT_COLOR = 1,0.494118,0.47451
    APPEARANCE_DEFINITION_STORAGE = CREATE
    APPEARANCE_NAME = InnerArrow
    DIFFUSE_COLOR = 1,0.14902,0
    GQUERY:
      for $geom in //geometry
      where $geom/@fme_geometry_name = 'core'
      return number($geom/@fme_id)
    SHININESS = 0.2
    SIDE_OPTION = BOTH
    SPECULAR_COLOR = 0.580392,0.0901961,0.317647
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> AppearanceSetter_5 [GEOMETRY]
    UNMATCHED -> AppearanceSetter_5 [GEOMETRY]
AppearanceSetter_5
    APPEARANCE_DEFINITION_STORAGE = CREATE
    APPEARANCE_NAME = OuterArrow
    DIFFUSE_COLOR = 0.129412,0.129412,0.129412
    GQUERY:
      for $geom in //geometry
      where $geom/@fme_geometry_name = 'outline'
      return number($geom/@fme_id)
    SHININESS = 0.2
    SIDE_OPTION = BOTH
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> Scaler

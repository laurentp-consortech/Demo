FME workspace HelloLizard.fmw
Title: HelloLizard
Description: Purpose & Objectives
This workspace displays a model of the FME Lizard mascot in the FME Realize app. The FME Lizard also has a summary annotation created when the user points at the model in the app.
Key Transformer 
AttributeCreator: Creates a summary annotation on the FME Lizard feature.
Data Source(s) - Reader Feature Type
OBJ Reader reads in the FME Lizard 3D model as a .obj file
Data Output - Writer Feature Type
FME AR Writer saves the geometry into a form that is overlaid on a live view in AR
Customization
To customize this workspace, you can change the following:
Attributes to display in AR as summary annotations with the AttributeCreator transformer
3D model of the FME Lizard with your own model
If you're recreating this workspace with your own data, it is recommended to build the workspace from scratch as your dataset will have different attributes and schema (structure).
Usage: For help with this workspace, please contact Safe Software Support and reference FME AR: Hello Lizard.

Readers:
- OBJ_3: OBJ from $(FME_MF_DIR)LizardsHoody2023.zip

Writers:
- FME_AR_1: FME_AR to FMELizard.fmear

Note: Purpose & Objectives / This workspace displays a model of the FME Lizard mascot in the FME Realize app. The FME Lizard also has a summary annotation created when the user points at the model in the app. / Key Transformer / AttributeCreator: Creates a summary annotation on the FME Lizard feature. / Data Source(s) - Reader Feature Type / OBJ Reader reads in the FME Lizard 3D model as a .obj file / Data Output - Writer Feature Type / FME AR Writer saves the geometry into a form that is overlaid on a live view in AR / Customization / To customize this workspace, you can change the following: / Attributes to display in AR as summary annotations with the AttributeCreator transformer / 3D model of the FME Lizard with your own model / If you're recreating this workspace with your own data, it is recommended to build the workspace from scratch as your dataset will have different attributes and schema (structure). / For help with this workspace, please contact Safe Software Support and reference FME AR: Hello Lizard.

Bookmark: Create Anchor
Note: This is a not real-world example, hence, we can place it anywhere in world, so the anchor "knows" its in-the-model location, but not the geolocation
Note: Creates a point two meters away from the Lizard, which will be where the observer is located.
Creator_2
    COORDS = 0 -3
    GEOMTYPE = 2D Coordinate List
    NUM = 1
    CREATED -> AttributeCreator_2
Note: Tells the AR model where the observer should be anchored.
AttributeCreator_2
    ATTR_TABLE = SET_TO fmear_location_feature (varchar(200)) = anchor
    -> Lizard (writer FME_AR_1)

Bookmark: Lizard
FMELizardLogo2023 (reader OBJ_3)
    -> AttributeCreator
Note: AttributeCreator [AttributeCreator] / New Attributes: Output AttributeValueTypefmear_feature_summary**FME Lizard** is happy to see you / in *Augmented Reality*. / `Welcome!` / [Visit Safe Software for more](https://www.safe.com)buffer
AttributeCreator
    ATTR_TABLE:
      SET_TO fmear_feature_summary (buffer) = **FME Lizard** is happy to see you
        in *Augmented Reality*.
        `Welcome!`
        [Visit Safe Software for more](https://www.safe.com)
    -> Lizard (writer FME_AR_1)
Note: Save or stream FMEAR file / in Full Scale (1:1)
Lizard (writer FME_AR_1)

Bookmark: Scenario
Note: The user will see a 3D model of the FME Lizard anchored 2 metres away from their device.

Bookmark: Running the Workspace - Step-by-step
Note: Step 1: / Change the summary annotations and appearance styling for the different infrastructure features (optional).
Note: Step 2: / Publish the workspace to FME Flow.
Note: Step 3: / On FME Flow, create a Flow AR App with this workspace.
Note: Step 4: / Open the FME Realize app on an iOS device. Connect to your FME Flow.
Note: Step 5: / Run the AR app created in Step 3 and visualize the data in augented reality.

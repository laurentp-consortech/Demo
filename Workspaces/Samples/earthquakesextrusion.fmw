FME workspace earthquakesextrusion.fmw
Title: Earthquakes: GeoJSON to KML Diagrams
Description: This workspace reads in earthquake data, converts magnitude values to a linear scale in order to use a custom transformer that creates features that will appear as a three-dimensional diagram when output to KML and opened in Google Earth, and then sorts and colors those diagrams based on magnitude value.
Published parameters allow the user to select:
Source file
History: 22-03-2023,Kate Brillinger,Updated transformers within custom transformer and added description

Parameters:
- SourceDataset_GEOJSON = http://earthquake.usgs.gov/earthquakes/feed/v1.0/summary/2.5_week.geojson   # Source GeoJSON File or URL

Readers:
- GEOJSON_1: GEOJSON from $(SourceDataset_GEOJSON)

Writers:
- OGCKML_1: OGCKML to E:/Safe Software/FMEFlow/resources/system/temp/engineresults\quakes.kml

2.5_week (reader GEOJSON_1)
    attributes: mag float, place string, time string, updated string, tz int, url string, felt string, cdi string, mmi string, alert string, status string, tsunami string, sig string, net string, code string, ids string, sources string, types string, nst string, dmin string, rms string, gap string, magnitudeType string
    -> ExpressionEvaluator_convert_magnitude_2
Note: Convert magnitude to a / linear scale.
ExpressionEvaluator_convert_magnitude_2
    ACTION = Create New Attribute
    EXPRESSION = @pow(10,@Value(mag))
    VAL_ATTR = magnitude
    -> KMLDiagrammer
Note: Create extruded diagrams with the height / dependent on the magnitude of the earthquake.
KMLDiagrammer
    KMLDiagrammerAttr = magnitude
    KMLDiagrammerScale = 1
    KMLDiagrammerShape = Round
    KMLDiagrammerSize = 0.5
    NAME = "@Value(place),  Magnitude: @Value(mag) "
    -> Sorter
Note: Sort the diagrams by earthquake magnitude.
Sorter
    SORT_PARM = mag NUMERIC DESCENDING
    SORTED -> FeatureColorSetter
Note: Color the diagrams
FeatureColorSetter
    COLOR = 1,0,0
    FILL_COLOR = 1,0,0
    MODE = Fixed
    COLORED -> Quakes (writer OGCKML_1)
Quakes (writer OGCKML_1)

FME custom transformer KMLDiagrammer
This transformer creates features that will appear as a three-dimensional diagram when output to KML and opened in Google Earth.
Published parameters allow the user to select:
Object shape (round or square) 
Object size 
Z-value attribute 
Z-value multiplier
Resulting features are located at the centre of the incoming feature.
Set feature size and shape using parameters. Because the output is intended for Google Earth, the size parameter only accepts decimal degrees as the units.

Parameters:
- KMLDiagrammerShape = Round   # Object Shape
- KMLDiagrammerSize = 0.5   # Object Size (Decimal Degrees)
- KMLDiagrammerAttr =   # " " Z Value Attribute
- KMLDiagrammerScale = 1   # Z Value Scale
- NAME = <auto>   # KML Name Attribute

INPUT (input)
    -> CoordinateSystemExtractor
AttributeRemover
    REMOVE_ATTRS = _KMLDiagrammerCoordSystem
    -> OUTPUT (output)
Note: This output port must / be ABOVE the other / in order to appear uppermost / in the canvas
OUTPUT (output)
Note: This output port must / be BELOW the other / in order to appear lowermost / in the canvas
REJECTED (output)

Bookmark: Confirm coordinate system and reproject to LL
CoordinateSystemExtractor
    CRDSYS_ATTR = _KMLDiagrammerCoordSystem
    -> Tester_2
Tester_2
    BOOL_OP = OR
    TEST_CLAUSE = TEST _KMLDiagrammerCoordSystem NOT_ATTRIBUTE_IS_EMPTY ""
    TEST_MODE = TEST
    PASSED -> Reprojector
    FAILED -> REJECTED (output)
Reprojector
    DEST = LL83
    INTERPOLATION_TYPE_NAME = Nearest Neighbor
    RASTER_CELL_SIZE = Preserve Cells
    RASTER_TOLERANCE = 0.0
    REPROJECTED -> CenterPointReplacer

Bookmark: Replace Geometry
CenterPointReplacer
    POINTTYPE = CENTER
    POINT -> 2DEllipseReplacer
2DEllipseReplacer
    PRIMAXIS = $(KMLDiagrammerSize)
    ROT = 0
    SECAXIS = $(KMLDiagrammerSize)
    ELLIPSE -> Tester
Tester
    BOOL_OP = OR
    TEST_CLAUSE = TEST $(KMLDiagrammerShape) = Round
    TEST_MODE = TEST
    PASSED -> 3DForcer
    FAILED -> BoundingBoxReplacer
BoundingBoxReplacer
    BOXTYPE = 2D Bounding Box
    BOX -> 3DForcer

Bookmark: Set up the KML components
3DForcer
    KEEPZVAL = No
    ZVALATTR = (@Value($(KMLDiagrammerAttr))*$(KMLDiagrammerScale))
    -> KMLPropertySetter
KMLPropertySetter
    ADD_ATTR_TABLE = Yes
    ALTITUDE_MODE = Relative To Ground
    ATTR_TABLE_TITLE = Attributes
    CONTENT_TYPE = Text
    EXTRUDE = Yes
    GEOM_TYPE = Vector
    NAME = $(NAME)
    SUMMARY = <none>
    TESSELATE = Yes
    VISIBILITY = Yes
    -> KMLStyler
KMLStyler
    FILL_COLOR = 1,0.666667,0
    FILL_OPACITY = 0.6
    ICON_OPACITY = 1.0
    ICON_SCALE = 0.8
    LABEL_OPACITY = 1.0
    LABEL_SCALE = 1.0
    LABEL_VISIBILITY = Yes
    LINE_WIDTH = 1.0
    LINE_WIDTH_UNITS = Pixels (Display Units)
    OPACITY = 1.0
    STYLE_PER_FEATURE = Yes
    KMLStyled -> AttributeRemover

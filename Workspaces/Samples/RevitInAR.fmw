FME workspace RevitInAR.fmw
Title: RevitInAR
Description: Purpose & Objectives
This workspace generates a dataset for an indoor scenario, either a living room or a kitchen, for displaying in augmented reality using the FME Realize app. User parameters, including contextual dependent parameters, are used to set the styling of the Revit features displayed in AR when running the app. 
Key Transformers
Clipper: Clips the Revit dataset to a selected room
AppearanceSetter: Sets appearance style(s) onto the sides of geometry surfaces 
RasterGeoreferencer: Sets the size of the texture to 1 by 1 m for applying as furniture upholstery
Data Source(s) - Reader Feature Type
Autodesk Revit Reader reads in Revit elements, including living room or kitchen surfaces and furniture
OBJ Reader reads in plumbing features, in the Wavefront Obj format, as 3D models
Autodesk 3ds Reader reads in 3D geometry of kitchen appliance data in 3ds format 
Data Output - Writer Feature Type
FME AR Writer saves the geometry into a form that is overlaid on a live view in AR
Customization
To customize this workspace, you can change the following:
Feature appearance (style, colour, texture) with the AppearanceSetter transformers
Attributes to display in AR as summary annotations with the AttributeCreator transformers
3D model data sources
If you're recreating this workspace with your own data, it is recommended to build the workspace from scratch as your dataset will have different attributes and schema (structure).
Usage: For help with this workspace, please contact Safe Software Support and reference FME AR: Revit in Augmented Reality.

Parameters:
- ROOM = 0b74b3fa-1a92-405e-9ac9-d59067bce2dd-0002ffa2   # Room,0b74b3fa-1a92-405e-9ac9-d59067bce2dd-0002ff9f Select Room
- APPLIANCECOLOR = StainlessSteel   # Steel,StainlessSteel Appliances Color
- CASEWORKCOLOR = 0.16,0.44,0.58   # Casework Color
- UPHOLSTERY = carpet   # Upholstery Pattern

Readers:
- REVITNATIVE_2: REVITNATIVE from $(FME_MF_DIR)Duplex_A.rvt
- JPEG_1: JPEG from ""$(FME_MF_DIR)geometric_pixabay.jpg" "$(FME_MF_DIR)carpet.jpg" "$(FME_MF_DIR)leaves_pixabay.jpg""
- OBJ_2: OBJ from $(FME_MF_DIR)PlumbingFixtures.obj
- 3DS_1: 3DS from $(FME_MF_DIR)Appl.3ds

Writers:
- FME_AR_1: FME_AR to FMEIndoor.fmear

Note: Purpose & Objectives / This workspace generates a dataset for an indoor scenario, either a living room or a kitchen, for displaying in augmented reality using the FME Realize app. User parameters, including contextual dependent parameters, are used to set the styling of the Revit features displayed in AR when running the app. / Key Transformers / Clipper : Clips the Revit dataset to a selected room / AppearanceSetter : Sets appearance style(s) onto the sides of geometry surfaces / RasterGeoreferencer : Sets the size of the texture to 1 by 1 m for applying as funiture upholstery / Data Source(s) - Reader Feature Type / Autodesk Revit Reader reads in Revit elements, including living room or kitchen surfaces and furniture / OBJ Reader reads in plumbing features, in the Wavefront Obj format, as 3D models / Autodesk 3ds Reader reads in 3D geometry of kitchen appliance data in 3ds format / Data Output - Writer Feature Type / FME AR Writer saves the geometry into a form that is overlaid on a live view in AR / Customization / To customize this workspace, you can change the following: / Feature appearance (style, colour, texture) with the AppearanceSetter transformers / Attributes to display in AR as summary annotations with the AttributeCreator transformers / 3D model data sources / If you're recreating this workspace with your own data, it is recommended to build the workspace from scratch as your dataset will have different attributes and schema (structure). / For help with this workspace, please contact Safe Software Support and reference FME AR: Bringing Revit to AR.
Note: Keep either kitchen on living room depending on a parameter choice / The parameter is hard-coded to two IDs particular rooms of the source Revit file
TestFilter_4
    DEFAULT_VALUE = <UNFILTERED>
    PASSED_TEST_GROUP_OUTPUT = FIRST
    TEST_LIST = "BOOL_OP,OR,COMPOSITE_TEST,""""""1"""""",TEST_CLAUSE,TEST @Value(UniqueId) = $(ROOM)",SelectedRoom
    SelectedRoom -> Scaler
Note: Make rooms slightly smaller. There is no wall between the kitchen and the living room areas, and, as a result, the Clipper will bring some kitchen features into the living room. Smaller clippers won't clip unnecessary features.
Scaler
    DISABLE_FACTORIES = *
    RASTER_SCALING = Extents
    TEXT_LOC_ONLY = Location and Size
    XSCALE = 0.9
    YSCALE = 0.9
    ZSCALE = 1
    SCALE_ORIGIN = Center Point
    SCALED -> Clipper [CLIPPER]
Note: Preserve geometry for later use. The easiest, but destructive way to find features within a room is to use Clipper (for 2D analysis, there are better tools such as SpatialFilter or SpatialRelator)
GeometryExtractor_2
    ATTR = _geometry
    KIND = fmebinary
    REMOVE_GEOMETRY = No
    KIND_LONG = FME Binary
    -> Clipper [CANDIDATE]
Note: Only objects belonging to the selected room will be inside. Clippint will destroy their geometry - see next step
Clipper
    ADD_NODATA = YES
    ATTR_ACCUM_MODE = MERGE
    ATTR_CONFLICT_RES = CANDIDATE
    BOUNDARY_CASES = INSIDE
    CLEANING_TOLERANCE_LOOKUP = AUTO
    CLIPPED_ATTR = _clipped
    CLIPPERS_FIRST = NO
    GENERATE_LIST = NO
    INVALID_PARTS_HANDLING = REJECT_WHOLE
    MISSING_M_MODE_LOOKUP = LINEAR
    MISSING_Z_MODE_LOOKUP = PLANAR
    MULTIPLE_CLIPPERS = YES
    M_VAL_SOURCE = CANDIDATE
    OVERLAPPING_CLIPPERS = CLIP_INTERIM
    PRESERVE_RASTER_EXTENTS = NO
    RASTER_CELL_MODE = CENTER
    Z_VAL_SOURCE = CANDIDATE
    CLEANING_TOLERANCE = Automatic
    MISSING_M_MODE = Linear Interpolation
    MISSING_Z_MODE = Planar Interpolation
    INSIDE -> CoordinateSystemRemover
Note: The AR writer needs either the same coordinate system on all features or no coordinate system at all. Revit reader adds XY-M coordinate system, which can be safely removed
CoordinateSystemRemover
    -> GeometryReplacer
Note: Restore the original geometry from the _geometry attribute
GeometryReplacer
    KIND = fmebinary
    REMOVE_ATTRIBUTE = Yes
    SOURCE = @Value(_geometry)
    KIND_LONG = FME Binary
    -> FeatureTypeFilter
Note: Split by feature type for separate processing
FeatureTypeFilter
    ATTRIBUTES = <Blank>,<Unfiltered>,Architectural.Furniture,Architectural.Casework,PlumbingFixtures,Appl
    ATTRIBUTE_INFO = Appl,3ds_mesh_name,Architectural.Casework,ObjectId,BuildingLevelElevation,BuildingLevelRoomOffset,BuildingLevelIsStory,BaseCategory,BuildingLevel,Category,Constraints.ElevationfromLevel,Constraints.Host,Constraints.Level,Constraints.MovesWithNearbyElements,Constraints.OffsetfromHost,Construction.BacksplashVisibility,Construction.ConstructionType,CreatedPhase,Dimensions.Area,Dimensions.CounterThickness,Dimensions.Depth,Dimensions.Height,Dimensions.Length,Dimensions.PlinthDepth,Dimensions.PlinthHeight,Dimensions.SinkLocation,Dimensions.SinkLocationToWall,Dimensions.SinkOpeningDepth,Dimensions.SinkOpeningWidth,Dimensions.TopOfCabinet,Dimensions.Volume,Dimensions.Width,Discipline,ElementType,Elevation,Family,FamilyType,Function,HostFeatureType,HostId,IFCParameters.ExportTypetoIFC,IFCParameters.ExportTypetoIFCAs,IFCParameters.ExporttoIFC,IFCParameters.ExporttoIFCAs,IFCParameters.IFCPredefinedType,IFCParameters.IfcExportAs,IFCParameters.IfcExportType,IFCParameters.IfcGUID,IFCParameters.TypeIFCPredefinedType,IFCParameters.TypeIfcGUID,IdentityData.AssemblyCode,IdentityData.AssemblyDescription,IdentityData.CodeName,IdentityData.Comments,IdentityData.Cost,IdentityData.Description,IdentityData.Image,IdentityData.Keynote,IdentityData.Manufacturer,IdentityData.Mark,IdentityData.Model,IdentityData.OmniClassNumber,IdentityData.OmniClassTitle,IdentityData.OmniclassNumber,IdentityData.OmniclassTitle,IdentityData.TypeComments,IdentityData.TypeImage,IdentityData.TypeMark,IdentityData.TypeName,IdentityData.URL,InExteriorShell,MaterialsandFinishes.CabinetMaterial,MaterialsandFinishes.CounterTopMaterial,MaterialsandFinishes.Door/DrawerMaterial,MaterialsandFinishes.Finish,MaterialsandFinishes.HandleMaterial,MaterialsandFinishes.PanelMaterial,Other.AccessibilityPerformance,Other.Area,Other.AssetAccountingType,Other.AssetIdentifier,Other.BarCode,Other.Category,Other.CodePerformance,Other.Color,Other.Constituents,Other.ExpectedLife,Other.Family,Other.FamilyName,Other.FamilyandType,Other.Features,Other.Finish,Other.Grade,Other.HostId,Other.InstallationDate,Other.Material,Other.ModelLabel,Other.ModelReference,Other.NominalHeight,Other.NominalLength,Other.NominalWidth,Other.ProductionYear,Other.Reference,Other.ReplacementCost,Other.SerialNumber,Other.Shape,Other.Size,Other.SustainabilityPerformance,Other.TagNumber,Other.Type,Other.TypeId,Other.WarrantyDescription,Other.WarrantyDurationLabor,Other.WarrantyDurationParts,Other.WarrantyGuarantorLabor,Other.WarrantyGuarantorParts,Other.WarrantyStartDate,Phasing.PhaseCreated,Phasing.PhaseDemolished,UniqueId,WorksetName,Architectural.Furniture,ObjectId,BuildingLevelElevation,BuildingLevelRoomOffset,BuildingLevelIsStory,BaseCategory,BuildingLevel,Category,Constraints.ElevationfromLevel,Constraints.Host,Constraints.Level,Constraints.MovesWithNearbyElements,CreatedPhase,Dimensions.Area,Dimensions.Height,Dimensions.Length,Dimensions.Volume,Dimensions.Width,Discipline,ElementType,Elevation,Family,FamilyType,Function,IFCParameters.ExportTypetoIFC,IFCParameters.ExportTypetoIFCAs,IFCParameters.ExporttoIFC,IFCParameters.ExporttoIFCAs,IFCParameters.IFCPredefinedType,IFCParameters.IfcExportAs,IFCParameters.IfcExportType,IFCParameters.IfcGUID,IFCParameters.TypeIFCPredefinedType,IFCParameters.TypeIfcGUID,IdentityData.AssemblyCode,IdentityData.AssemblyDescription,IdentityData.CodeName,IdentityData.Comments,IdentityData.Cost,IdentityData.Description,IdentityData.Image,IdentityData.Keynote,IdentityData.Manufacturer,IdentityData.Mark,IdentityData.Model,IdentityData.OmniClassNumber,IdentityData.OmniClassTitle,IdentityData.OmniclassNumber,IdentityData.OmniclassTitle,IdentityData.TypeComments,IdentityData.TypeImage,IdentityData.TypeMark,IdentityData.TypeName,IdentityData.URL,InExteriorShell,MaterialsandFinishes.FrameMaterial,MaterialsandFinishes.LegMaterial,MaterialsandFinishes.MattressMaterial,MaterialsandFinishes.SeatMaterial,MaterialsandFinishes.TopMaterial,Other.AccessibilityPerformance,Other.Area,Other.AssetAccountingType,Other.AssetIdentifier,Other.BarCode,Other.Category,Other.CodePerformance,Other.Color,Other.Constituents,Other.ExpectedLife,Other.Family,Other.FamilyName,Other.FamilyandType,Other.Features,Other.Finish,Other.Grade,Other.InstallationDate,Other.Material,Other.ModelLabel,Other.ModelReference,Other.NominalHeight,Other.NominalLength,Other.NominalWidth,Other.ProductionYear,Other.Reference,Other.ReplacementCost,Other.SerialNumber,Other.Shape,Other.Size,Other.SustainabilityPerformance,Other.TagNumber,Other.Type,Other.TypeId,Other.WarrantyDescription,Other.WarrantyDurationLabor,Other.WarrantyDurationParts,Other.WarrantyGuarantorLabor,Other.WarrantyGuarantorParts,Other.WarrantyStartDate,Phasing.PhaseCreated,Phasing.PhaseDemolished,UniqueId,WorksetName,Architectural.Rooms,ObjectId,BuildingLevelElevation,BuildingLevelRoomOffset,BuildingLevelIsStory,Dimensions.RoomArea,BaseCategory,BuildingLevel,Category,Constraints.BaseOffset,Constraints.Level,Constraints.LimitOffset,Constraints.UpperLimit,Dimensions.Area,Dimensions.ComputationHeight,Dimensions.Perimeter,Dimensions.UnboundedHeight,Dimensions.Volume,Discipline,ElementType,EnergyAnalysis.ActualLightingLoad,EnergyAnalysis.ActualLightingLoadperarea,EnergyAnalysis.ActualPowerLoad,EnergyAnalysis.ActualPowerLoadperarea,EnergyAnalysis.AreaperPerson,EnergyAnalysis.BaseLightingLoadon,EnergyAnalysis.BasePowerLoadon,EnergyAnalysis.CalculatedCoolingLoadperarea,EnergyAnalysis.CalculatedHeatingLoadperarea,EnergyAnalysis.HeatLoadValues,EnergyAnalysis.LatentHeatGainperperson,EnergyAnalysis.LightingLoadUnits,EnergyAnalysis.NumberofPeople,EnergyAnalysis.OccupancyUnit,EnergyAnalysis.PlenumLightingContribution,EnergyAnalysis.PowerLoadUnits,EnergyAnalysis.SensibleHeatGainperperson,EnergyAnalysis.SpecifiedLightingLoad,EnergyAnalysis.SpecifiedLightingLoadperarea,EnergyAnalysis.SpecifiedPowerLoad,EnergyAnalysis.SpecifiedPowerLoadperarea,EnergyAnalysis.TotalHeatGainperperson,Family,FamilyType,IFCParameters.ExporttoIFC,IFCParameters.ExporttoIFCAs,IFCParameters.IFCPredefinedType,IFCParameters.IfcGUID,IdentityData.AssemblyCode,IdentityData.AssemblyDescription,IdentityData.Comments,IdentityData.Image,IdentityData.Name,IdentityData.Number,IdentityData.OmniClassTable13Category,IdentityData.RoomName,IdentityData.RoomNumber,IdentityData.TypeName,InExteriorShell,Mechanical-Flow.CalculatedSupplyAirflowperarea,Other.Category,Other.CategoryCode,Other.CategoryDescription,Other.CeilingCovering,Other.CirculationZoneName,Other.FamilyName,Other.FireAlarmZoneName,Other.FloorCovering,Other.HistoricPreservationZoneName,Other.LightingZoneName,Other.LoadCapacity,Other.OccupancyZoneName,Other.PhaseId,Other.RoomTag,Other.VentilationZoneName,Other.WallCovering,Phasing.Phase,UniqueId,WorksetName,PlumbingFixtures,
    Architectural.Furniture -> AppearanceSetter_2 [GEOMETRY]
    Architectural.Casework -> Sampler_2
    Architectural.Casework -> AttributeCreator_4
    PlumbingFixtures -> AppearanceSetter_5 [GEOMETRY]
    Appl -> Counter

Bookmark: Revit reading
Architectural.Rooms (reader REVITNATIVE_2)
    attributes: ObjectId number(10,0), BuildingLevelElevation number(31,15), BuildingLevelRoomOffset number(31,15), BuildingLevelIsStory char(3), Dimensions.RoomArea number(31,15), BaseCategory char(5), BuildingLevel char(7), COBieComponentsSchedule.Room:Name char(11), COBieSpacesSchedule(Rooms).Area number(31,15), COBieSpacesSchedule(Rooms).CategoryCode char(8), COBieSpacesSchedule(Rooms).CategoryDescription char(13), COBieSpacesSchedule(Rooms).CeilingCovering char(15), COBieSpacesSchedule(Rooms).CirculationZoneName char(26), COBieSpacesSchedule(Rooms).FireAlarmZoneName char(24), COBieSpacesSchedule(Rooms).FloorCovering char(13), COBieSpacesSchedule(Rooms).HistoricPreservationZoneName char(35), COBieSpacesSchedule(Rooms).LightingZoneName char(23), COBieSpacesSchedule(Rooms).LoadCapacity char(12), COBieSpacesSchedule(Rooms).Name char(11), COBieSpacesSchedule(Rooms).Number char(4), COBieSpacesSchedule(Rooms).OccupancyZoneName char(24), COBieSpacesSchedule(Rooms).RoomTag char(7), COBieSpacesSchedule(Rooms).UnboundedHeight number(31,15), COBieSpacesSchedule(Rooms).VentilationZoneName char(26), COBieSpacesSchedule(Rooms).WallCovering char(12), COBieTypesSchedule.Manufacturer char(0), Category char(5), Constraints.BaseOffset number(31,15), Constraints.Level char(7), Constraints.LimitOffset number(31,15),
      Constraints.UpperLimit char(7), Dimensions.Area number(31,15), Dimensions.ComputationHeight number(31,15), Dimensions.Perimeter number(31,15), Dimensions.UnboundedHeight number(31,15), Dimensions.Volume number(31,15), Discipline char(13), ElementType char(8), EnergyAnalysis.ActualLightingLoad number(31,15), EnergyAnalysis.ActualLightingLoadperarea number(31,15), EnergyAnalysis.ActualPowerLoad number(31,15), EnergyAnalysis.ActualPowerLoadperarea number(31,15), EnergyAnalysis.AreaperPerson number(31,15), EnergyAnalysis.BaseLightingLoadon number(10,0), EnergyAnalysis.BasePowerLoadon number(10,0), EnergyAnalysis.CalculatedCoolingLoadperarea char(0), EnergyAnalysis.CalculatedHeatingLoadperarea char(0), EnergyAnalysis.HeatLoadValues number(10,0), EnergyAnalysis.LatentHeatGainperperson number(31,15), EnergyAnalysis.LightingLoadUnits number(10,0), EnergyAnalysis.NumberofPeople number(31,15), EnergyAnalysis.OccupancyUnit char(0), EnergyAnalysis.PlenumLightingContribution number(31,15), EnergyAnalysis.PowerLoadUnits number(10,0), EnergyAnalysis.SensibleHeatGainperperson number(31,15), EnergyAnalysis.SpecifiedLightingLoad number(31,15), EnergyAnalysis.SpecifiedLightingLoadperarea number(31,15), EnergyAnalysis.SpecifiedPowerLoad number(31,15), EnergyAnalysis.SpecifiedPowerLoadperarea number(31,15), EnergyAnalysis.TotalHeatGainperperson number(31,15),
      Family char(0), FamilyType char(0), IFCParameters.ExporttoIFC number(10,0), IFCParameters.ExporttoIFCAs char(0), IFCParameters.IFCPredefinedType char(0), IFCParameters.IfcGUID char(22), IdentityData.AssemblyCode char(0), IdentityData.AssemblyDescription char(0), IdentityData.Comments char(0), IdentityData.Image char(0), IdentityData.Name char(11), IdentityData.Number char(4), IdentityData.OmniClassTable13Category char(23), IdentityData.RoomName char(11), IdentityData.RoomNumber char(4), IdentityData.TypeName char(0), InExteriorShell char(3), Mechanical-Flow.CalculatedSupplyAirflowperarea char(0), Other.Category char(5), Other.CategoryCode char(8), Other.CategoryDescription char(13), Other.CeilingCovering char(15), Other.CirculationZoneName char(26), Other.FamilyName char(0), Other.FireAlarmZoneName char(24), Other.FloorCovering char(13), Other.HistoricPreservationZoneName char(35), Other.LightingZoneName char(23), Other.LoadCapacity char(12), Other.OccupancyZoneName char(24),
      Other.PhaseId char(16), Other.RoomTag char(7), Other.VentilationZoneName char(26), Other.WallCovering char(12), Phasing.Phase char(16), RoomKeySchedule-OmniClassTable13.CategoryCode char(8), RoomKeySchedule-OmniClassTable13.CategoryDescription char(13), RoomKeySchedule-OmniClassTable13.KeyName char(23), UniqueId char(45), WorksetName char(46)
    -> TestFilter_4
Architectural.Casework (reader REVITNATIVE_2)
    attributes: ObjectId number(10,0), BuildingLevelElevation number(31,15), BuildingLevelRoomOffset number(31,15), BuildingLevelIsStory char(3), BaseCategory char(8), BuildingLevel char(7), COBieComponentsSchedule.AssetIdentifier char(15), COBieComponentsSchedule.BarCode char(7), COBieComponentsSchedule.InstallationDate char(16), COBieComponentsSchedule.SerialNumber char(12), COBieComponentsSchedule.TagNumber char(9), COBieComponentsSchedule.WarrantyStartDate char(17), COBieTypesSchedule.Manufacturer char(0), COBieTypesSchedule.OmniClassNumber char(17), COBieTypesSchedule.OmniClassTitle char(16), Category char(8), Constraints.DefaultElevation number(31,15), Constraints.ElevationfromLevel number(31,15), Constraints.Host char(49), Constraints.Level char(7), Constraints.MovesWithNearbyElements boolean, Constraints.OffsetfromHost number(31,15), Construction.BacksplashVisibility boolean, Construction.ConstructionType char(17), CreatedPhase char(16), Dimensions.Area number(31,15), Dimensions.CounterThickness number(31,15), Dimensions.Depth number(31,15), Dimensions.Height number(31,15), Dimensions.Length number(31,15),
      Dimensions.PlinthDepth number(31,15), Dimensions.PlinthHeight number(31,15), Dimensions.SinkLocation number(31,15), Dimensions.SinkLocationToWall number(31,15), Dimensions.SinkOpeningDepth number(31,15), Dimensions.SinkOpeningWidth number(31,15), Dimensions.TopOfCabinet number(31,15), Dimensions.Volume number(31,15), Dimensions.Width number(31,15), Discipline char(13), ElementType char(14), Elevation number(31,15), Family char(29), FamilyType char(6), Function char(8), HostFeatureType char(19), HostId number(10,0), IFCParameters.ExportTypetoIFC number(10,0), IFCParameters.ExportTypetoIFCAs char(0), IFCParameters.ExporttoIFC number(10,0), IFCParameters.ExporttoIFCAs char(0), IFCParameters.IFCPredefinedType char(0), IFCParameters.IfcExportAs char(0), IFCParameters.IfcExportType char(0), IFCParameters.IfcGUID char(22), IFCParameters.TypeIFCPredefinedType char(0), IFCParameters.TypeIfcGUID char(22), IdentityData.AssemblyCode char(0), IdentityData.AssemblyDescription char(0), IdentityData.CodeName char(0),
      IdentityData.Comments char(0), IdentityData.Cost char(0), IdentityData.Description char(0), IdentityData.Image char(0), IdentityData.Keynote char(0), IdentityData.Manufacturer char(12), IdentityData.Mark char(0), IdentityData.Model char(0), IdentityData.OmniClassNumber char(17), IdentityData.OmniClassTitle char(16), IdentityData.OmniclassNumber char(17), IdentityData.OmniclassTitle char(16), IdentityData.TypeComments char(0), IdentityData.TypeImage char(0), IdentityData.TypeMark char(0), IdentityData.TypeName char(6), IdentityData.URL char(0), InExteriorShell char(3), MaterialsandFinishes.CabinetMaterial char(13), MaterialsandFinishes.CounterTopMaterial char(13), MaterialsandFinishes.Door/DrawerMaterial char(13), MaterialsandFinishes.Finish char(6), MaterialsandFinishes.HandleMaterial char(18), MaterialsandFinishes.PanelMaterial char(16), Other.AccessibilityPerformance char(24), Other.Area char(4), Other.AssetAccountingType char(5), Other.AssetIdentifier char(15), Other.BarCode char(7), Other.Category char(8),
      Other.CodePerformance char(15), Other.Color char(5), Other.Constituents char(12), Other.ExpectedLife char(12), Other.Family char(29), Other.FamilyName char(29), Other.FamilyandType char(38), Other.Features char(8), Other.Finish char(6), Other.Grade char(5), Other.HostId char(32), Other.InstallationDate char(16), Other.Material char(8), Other.ModelLabel char(10), Other.ModelReference char(14), Other.NominalHeight char(13), Other.NominalLength char(13), Other.NominalWidth char(12), Other.ProductionYear char(14), Other.Reference char(9), Other.ReplacementCost char(15), Other.SerialNumber char(12), Other.Shape char(5), Other.Size char(4), Other.SustainabilityPerformance char(25), Other.TagNumber char(9), Other.Type char(6), Other.TypeId char(6), Other.WarrantyDescription char(19), Other.WarrantyDurationLabor char(21),
      Other.WarrantyDurationParts char(21), Other.WarrantyGuarantorLabor char(22), Other.WarrantyGuarantorParts char(22), Other.WarrantyStartDate char(17), Phasing.PhaseCreated char(16), Phasing.PhaseDemolished char(4), UniqueId char(45), WorksetName char(46)
    -> GeometryExtractor_2
Architectural.Furniture (reader REVITNATIVE_2)
    attributes: ObjectId number(10,0), BuildingLevelElevation number(31,15), BuildingLevelRoomOffset number(31,15), BuildingLevelIsStory char(3), BaseCategory char(9), BuildingLevel char(7), COBieComponentsSchedule.AssetIdentifier char(15), COBieComponentsSchedule.BarCode char(7), COBieComponentsSchedule.InstallationDate char(16), COBieComponentsSchedule.SerialNumber char(12), COBieComponentsSchedule.TagNumber char(9), COBieComponentsSchedule.WarrantyStartDate char(17), COBieTypesSchedule.Manufacturer char(0), COBieTypesSchedule.OmniClassNumber char(17), COBieTypesSchedule.OmniClassTitle char(14), Category char(9), Constraints.DefaultElevation number(31,15), Constraints.ElevationfromLevel number(31,15), Constraints.Host char(27), Constraints.Level char(7), Constraints.MovesWithNearbyElements boolean, CreatedPhase char(16), Dimensions.Area number(31,15), Dimensions.Height number(31,15), Dimensions.Length number(31,15), Dimensions.Volume number(31,15), Dimensions.Width number(31,15), Discipline char(13), ElementType char(14), Elevation number(31,15),
      Family char(6), FamilyType char(6), Function char(8), IFCParameters.ExportTypetoIFC number(10,0), IFCParameters.ExportTypetoIFCAs char(0), IFCParameters.ExporttoIFC number(10,0), IFCParameters.ExporttoIFCAs char(0), IFCParameters.IFCPredefinedType char(0), IFCParameters.IfcExportAs char(0), IFCParameters.IfcExportType char(0), IFCParameters.IfcGUID char(22), IFCParameters.TypeIFCPredefinedType char(0), IFCParameters.TypeIfcGUID char(22), IdentityData.AssemblyCode char(0), IdentityData.AssemblyDescription char(0), IdentityData.CodeName char(0), IdentityData.Comments char(0), IdentityData.Cost char(0), IdentityData.Description char(0), IdentityData.Image char(0), IdentityData.Keynote char(0), IdentityData.Manufacturer char(12), IdentityData.Mark char(0), IdentityData.Model char(0), IdentityData.OmniClassNumber char(17), IdentityData.OmniClassTitle char(14), IdentityData.OmniclassNumber char(17), IdentityData.OmniclassTitle char(14), IdentityData.TypeComments char(0), IdentityData.TypeImage char(0),
      IdentityData.TypeMark char(0), IdentityData.TypeName char(6), IdentityData.URL char(0), InExteriorShell char(3), MaterialsandFinishes.FrameMaterial char(13), MaterialsandFinishes.LegMaterial char(14), MaterialsandFinishes.MattressMaterial char(15), MaterialsandFinishes.SeatMaterial char(23), MaterialsandFinishes.TopMaterial char(14), Other.AccessibilityPerformance char(24), Other.Area char(4), Other.AssetAccountingType char(8), Other.AssetIdentifier char(15), Other.BarCode char(7), Other.Category char(9), Other.CodePerformance char(15), Other.Color char(5), Other.Constituents char(12), Other.ExpectedLife char(12), Other.Family char(6), Other.FamilyName char(6), Other.FamilyandType char(15), Other.Features char(8), Other.Finish char(6), Other.Grade char(5), Other.InstallationDate char(16), Other.Material char(8), Other.ModelLabel char(10), Other.ModelReference char(14), Other.NominalHeight char(13),
      Other.NominalLength char(13), Other.NominalWidth char(12), Other.ProductionYear char(14), Other.Reference char(9), Other.ReplacementCost char(15), Other.SerialNumber char(12), Other.Shape char(5), Other.Size char(4), Other.SustainabilityPerformance char(25), Other.TagNumber char(9), Other.Type char(6), Other.TypeId char(6), Other.WarrantyDescription char(19), Other.WarrantyDurationLabor char(21), Other.WarrantyDurationParts char(21), Other.WarrantyGuarantorLabor char(22), Other.WarrantyGuarantorParts char(22), Other.WarrantyStartDate char(17), Phasing.PhaseCreated char(16), Phasing.PhaseDemolished char(4), UniqueId char(45), WorksetName char(46)
    -> GeometryExtractor_2

Bookmark: OBJ reading (kitchen sink)
PlumbingFixtures (reader OBJ_2)
    -> GeometryExtractor_2

Bookmark: 3DS reading (Kitchen appliances)
Appl (reader 3DS_1)
    -> GeometryExtractor_2

Bookmark: Format feature appearance and set summary annotations for AR display
Note: Only one appearance is needed for all features
Sampler_2
    MODE = ORIGINAL
    RATE = 1
    SAMPLE_TYPE_MULTIPLIER = -1
    SAMPLE_MODE = No
    SAMPLE_TYPE_LONG = First N Features
    SAMPLED -> AttributeCreator_3
Note: Get casework color from a parameter
AttributeCreator_3
    ATTR_TABLE = SET_TO _color (varchar(200)) = $(CASEWORKCOLOR)
    -> AppearanceStyler_2
Note: Define casework colors
AppearanceStyler_2
    ALPHA = 1.0
    AMBIENT_COLOR = @Value(_color)
    APPEARANCE_NAME = Cabinets
    DIFFUSE_COLOR = @Value(_color)
    SHININESS = 0.2
    SPECULAR_COLOR = 0.137255,0.137255,0.137255
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP = REPEAT_BOTH
    TEXTURE_WRAP_DISPLAY = Repeat in U and V
    -> AppearanceSetter [APPEARANCE]
Note: Create summary annotations
AttributeCreator_4
    ATTR_TABLE:
      SET_TO fmear_feature_summary (varchar(200)) = Object ID: @Value(ObjectId)
        @Value(Family)
    -> AppearanceSetter [GEOMETRY]
Note: Set appearance on casework
AppearanceSetter
    APPEARANCE_DEFINITION_STORAGE = CREATE
    GQUERY:
      for $geom in //geometry
      where fme:appearance-front($geom)/@name = 'Cabinets'
      return number($geom/@fme_id)
    SIDE_OPTION = BOTH
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> AppearanceSetter_6 [GEOMETRY]
    UNMATCHED -> AppearanceSetter_6 [GEOMETRY]
Note: Set appearance on casework door and drawer handles
AppearanceSetter_6
    AMBIENT_COLOR = 0.662745,0.662745,0.662745
    APPEARANCE_DEFINITION_STORAGE = CREATE
    APPEARANCE_NAME = Handles
    DIFFUSE_COLOR = 0.752941,0.752941,0.752941
    GQUERY:
      for $geom in //geometry
      where fme:appearance-front($geom)/@name = 'Cabinets - Handles'
      return number($geom/@fme_id)
    SHININESS = 0.95
    SIDE_OPTION = BOTH
    SPECULAR_COLOR = 1,1,1
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> Casework (writer FME_AR_1)
    UNMATCHED -> Casework (writer FME_AR_1)
Note: Style sink
AppearanceSetter_5
    AMBIENT_COLOR = 0.5,0.5,0.5
    APPEARANCE_DEFINITION_STORAGE = CREATE
    APPEARANCE_NAME = Sink
    DIFFUSE_COLOR = 0.7,0.7,0.7
    GQUERY:
      for $geom in //geometry
      where $geom/@fme_geometry_name = ''
      return number($geom/@fme_id)
    SHININESS = 0.9
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> AttributeCreator_6
Note: Create summary annotation
AttributeCreator_6
    ATTR_TABLE:
      SET_TO fmear_feature_summary (varchar(234)) = Object ID: 582920
        M_Sink - Island - Single
    -> Sink (writer FME_AR_1)
Note: Add upholstery to couches. The pattern will repeat every meter.
AppearanceSetter_2
    APPEARANCE_DEFINITION_STORAGE = CREATE
    APPEARANCE_NAME = CouchFabric
    GQUERY:
      for $geom in //geometry
      where fme:appearance-front($geom)/@name = 'Textile - Linen, Smooth'
      return number($geom/@fme_id)
    SHININESS = 0.2
    SIDE_OPTION = BOTH
    SPECULAR_COLOR = 0.47451,0.47451,0.47451
    TEXTURE_MAPPING_TYPE = SURFACE_NORMAL_GROUNDUNITS
    TEXTURE_U_OFFSET2 = 0.0
    TEXTURE_V_OFFSET2 = 0.0
    USE_EXISTING_TEXTURE_COORDINATES_OPTION = NO
    DEF_STORAGE = Create New Definitions
    SET_ON_SIDE = Front and Back Sides
    TEXTURE_MAPPING_TYPE_CHOICE = Surface Normal in Ground Units
    USE_EXISTING_TEXTURE_COORDINATES = No
    -> AppearanceSetter_7 [GEOMETRY]
    UNMATCHED -> AppearanceSetter_7 [GEOMETRY]
Note: Create summary annotation
AttributeCreator_2
    ATTR_TABLE:
      SET_TO fmear_feature_summary (varchar(200)) = Object ID: @Value(ObjectId)
        @Value(Family)
    -> Furniture (writer FME_AR_1)
Note: Define appliance appearance
AppearanceStyler
    ALPHA = 1.0
    AMBIENT_COLOR = @Value(_ambient_color)
    APPEARANCE_NAME = ApplianceColors
    DIFFUSE_COLOR = @Value(_diffuse_color)
    SHININESS = @Value(_shininess)
    SPECULAR_COLOR = @Value(_specular_color)
    TEXTURE_CENTER_U = 0.0
    TEXTURE_CENTER_V = 0.0
    TEXTURE_ROTATION_ANGLE = 0.0
    TEXTURE_U_OFFSET = 0.0
    TEXTURE_U_SCALING_FACTOR = 1.0
    TEXTURE_U_SHEARING_FACTOR = 0.0
    TEXTURE_V_OFFSET = 0.0
    TEXTURE_V_SCALING_FACTOR = 1.0
    TEXTURE_V_SHEARING_FACTOR = 0.0
    TEXTURE_WRAP = REPEAT_BOTH
    TEXTURE_WRAP_DISPLAY = Repeat in U and V
    -> AppearanceSetter_3 [APPEARANCE]
Note: Set appearances on appliances
AppearanceSetter_3
    APPEARANCE_DEFINITION_STORAGE = CREATE
    GQUERY:
      for $geom in //geometry
      where fme:appearance-front($geom)/@name = 'Metal01'
      or fme:appearance-front($geom)/@name = 'Laminate'
      or fme:appearance-front($geom)/@name = 'Metal02'
      return number($geom/@fme_id)
    SIDE_OPTION = BOTH
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> AppearanceSetter_4 [GEOMETRY]
Note: Set a separate appearance on glass in microwave and oven
AppearanceSetter_4
    ALPHA = 0.25
    AMBIENT_COLOR = 0,0.627451,0.8
    APPEARANCE_DEFINITION_STORAGE = CREATE
    APPEARANCE_NAME = Glass
    DIFFUSE_COLOR = 0,0.666667,1
    GQUERY:
      for $geom in //geometry
      where fme:appearance-front($geom)/@name = 'Glass'
      return number($geom/@fme_id)
    SHININESS = 0.8
    SIDE_OPTION = FRONT
    SPECULAR_COLOR = 0.839216,0.839216,0.839216
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front Side
    TEXTURE_MAPPING_TYPE_CHOICE = Surface Normal
    USE_EXISTING_TEXTURE_COORDINATES = No
    -> Appliances (writer FME_AR_1)
    UNMATCHED -> Appliances (writer FME_AR_1)

Bookmark: New Bookmark
Note: Save casework asset to FMEAR file if kitchen room is selected
Casework (writer FME_AR_1)
Note: Save sink asset to FMEAR file / if kitchen is selected
Sink (writer FME_AR_1)
Note: Save furniture asset to FMEAR file (if living room is selected)
Furniture (writer FME_AR_1)
Note: Save appliances asset to FMEAR file (if kitchen room is selected)
Appliances (writer FME_AR_1)

Bookmark: Setting summary annotation attributes for each appliance
Note: Normally, these values come from attributes (Revit, IFC) or external sources (databases, spreadsheets)
Counter
    CNT_ATTR = _appl_count
    DOMAIN = counter
    SCOPE = Global
    START = 0
    -> AttributeValueMapper_5
AttributeValueMapper_5
    LUT:
      0,**Object ID:** 575374
      **Refrigerator Model:** LizardFreeze 1200LE
      **Dimensions:** 850x760x1830mm
      **Color:** *$(APPLIANCECOLOR)*,1,**Object ID:** 575493
      **Range Model:** LizardHeat 640SE
      **Dimensions:** 760x650x1040mm
      **Color:** *$(APPLIANCECOLOR)*,2,**Object ID:** 615603
      **Microwave Oven Model:** LizardWave 305
      **Dimensions:** 760x400x450mm0
      **Color:** *$(APPLIANCECOLOR)*
    MAPPING_DIRECTION = FORWARD
    SRC = _appl_count
    VAL_ATTR = fmear_feature_summary
    -> AppearanceSetter_3 [GEOMETRY]

Bookmark: Preparing couch upholstery texture
Note: Read available textures
JPEG (reader JPEG_1)
    -> TestFilter
Note: Keep only one specified in user parameters
TestFilter
    DEFAULT_VALUE = <UNFILTERED>
    PASSED_TEST_GROUP_OUTPUT = FIRST
    TEST_LIST = "BOOL_OP,OR,COMPOSITE_TEST,""""""1"""""",TEST_CLAUSE,TEST @Value(fme_basename) = $(UPHOLSTERY)",Texture
    Texture -> RasterGeoreferencer
Note: Setting the size of the upholstery to 1x1 m - this size will be used to place the texture on couches
RasterGeoreferencer
    POINTANDANGLE_OR_EXTENTS = Extents
    X_LL_COORD = 0
    X_LR_COORD = 1
    X_UL_COORD = 0
    X_UR_COORD = 1
    Y_LL_COORD = -1
    Y_LR_COORD = -1
    Y_UL_COORD = 0
    Y_UR_COORD = 0
    -> AppearanceSetter_2 [APPEARANCE]

Bookmark: Set appearances on wooden parts
AppearanceSetter_7
    AMBIENT_COLOR = 0.6,0.443137,0.47451
    APPEARANCE_DEFINITION_STORAGE = CREATE
    APPEARANCE_NAME = Wood1
    DIFFUSE_COLOR = 0.580392,0.0666667,0
    GQUERY:
      for $geom in //geometry
      where fme:appearance-front($geom)/@name = 'Wood - Cherry'
      return number($geom/@fme_id)
    SHININESS = 0.9
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> AppearanceSetter_8 [GEOMETRY]
    UNMATCHED -> AppearanceSetter_8 [GEOMETRY]
AppearanceSetter_8
    AMBIENT_COLOR = 0.615686,0.521569,0.380392
    APPEARANCE_DEFINITION_STORAGE = CREATE
    APPEARANCE_NAME = Wood2
    DIFFUSE_COLOR = 0.580392,0.321569,0
    GQUERY:
      for $geom in //geometry
      where fme:appearance-front($geom)/@name = 'Wood - Teak'
      return number($geom/@fme_id)
    SHININESS = 0.9
    SIDE_OPTION = BOTH
    SPECULAR_COLOR = 0.921569,0.921569,0.921569
    TEXTURE_MAPPING_TYPE = SURFACE_NORMAL
    TEXTURE_U_OFFSET2 = 0.0
    TEXTURE_U_SCALE_FACTOR = 1.0
    TEXTURE_V_OFFSET2 = 0.0
    TEXTURE_V_SCALE_FACTOR = 1.0
    USE_EXISTING_TEXTURE_COORDINATES_OPTION = NO
    DEF_STORAGE = Create New Definitions
    SET_ON_SIDE = Front and Back Sides
    TEXTURE_MAPPING_TYPE_CHOICE = Surface Normal
    USE_EXISTING_TEXTURE_COORDINATES = No
    -> AttributeCreator_2
    UNMATCHED -> AttributeCreator_2

Bookmark: Creating colors
Creator_2
    GEOMTYPE = Geometry Object
    NUM = 1
    CREATED -> AttributeCreator
AttributeCreator
    ATTR_TABLE = SET_TO _color (varchar(200)) = $(APPLIANCECOLOR)
    -> AttributeValueMapper
AttributeValueMapper
    LUT = Black,0.1,0.1,0.1,White,1,1,1,StainlessSteel,0.7,0.7,0.7
    MAPPING_DIRECTION = FORWARD
    SRC = _color
    VAL_ATTR = _diffuse_color
    -> AttributeValueMapper_2
AttributeValueMapper_2
    LUT = Black,0.01,0.01,0.01,White,0.9,0.9,0.9,StainlessSteel,0.5,0.5,0.5
    MAPPING_DIRECTION = FORWARD
    SRC = _color
    VAL_ATTR = _ambient_color
    -> AttributeValueMapper_3
Note: Create diffuse, ambient, and specular colors as well as shininess for black/white/stainless steel appliances depending on appliances color parameter
AttributeValueMapper_3
    LUT = Black,0.5,0.5,0.5,White,0.8,0.8,0.8,StainlessSteel,0.9,0.9,0.9
    MAPPING_DIRECTION = FORWARD
    SRC = _color
    VAL_ATTR = _specular_color
    -> AttributeValueMapper_4
AttributeValueMapper_4
    LUT = Black,0.7,White,0.8,StainlessSteel,0.9
    MAPPING_DIRECTION = FORWARD
    SRC = _color
    VAL_ATTR = _shininess
    -> AppearanceStyler

Bookmark: Scenario
Note: The user will see a room - depending on their choice, either a kitchen or a living room. It is recommended to / explore the scene in a room with enough open space so that the augmented features do not interfere with real ones, and to avoid the risk of hitting real objects hidden behind augmentation.
Note: The user can choose the color of kitchen furniture as well they can pick one of three appliance colors - black, white, or stainless steel. For the living room, the user can select one of three upholstery options.
Note: The user can align the model to an existing wall or corner of a room or place the model in the middle of their room. If the user points the device to one of the appliances, they can inspect the summary annotations.

Bookmark: Running the Workspace - Step-by-step
Note: Step 1: / Set the source data for the 3D models to be displayed in AR. Change the summary annotations and appearance styling for the different features (optional).
Note: Step 2: / Publish the workspace to FME Flow.
Note: Step 3: / On FME Flow, create a Flow AR App with this workspace.
Note: Step 4: / Open the FME Realize app on an iOS device. Connect to your FME Flow.
Note: Step 5: / Run the AR app created in Step 3 and visualize the data in augented reality. Adjust the model to fit the existing room if necessary.

Bookmark: Appliances and plumbing fixtures
Note: For faster reading or for trying different models, we can replace revit assets with models from other formats/sources.

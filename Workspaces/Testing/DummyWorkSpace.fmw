FME workspace DummyWorkSpace.fmw

Creator
    GEOMTYPE = No Geometry
    NUM = 1
    CREATED -> Tester
    CREATED -> FeatureReader [INITIATOR]
Note: 1. FME Flow as connection storage / 2. ALWAYS usin DB & Web Connections through Deployment Parameters / 3. ALWAYS get latest commit from main / 4. ALWAYS work on workspaces from your local DEV branch / 5. Use regular commits and when publishing to FME UA, make sure to push to remote UA as well / 5. When moving workflow from UA to PROD create project, download it and push it to Github main branch
FeatureReader
    ATTRIBUTES = ENTAGE.ACCOUNT_FACT,"OBJECTID,ACCOUNT_NO,STATE_PARCEL_NO,ACCOUNT_SUBTYPE_CODE,TAX_DISTRICT_NO,LAND_ECONOMIC_AREA_CODE,ACCOUNT_TYPE,SUB_FILING_RECORDING_NO,OWNER_NAME,ADDRESS_LINE_1,ADDRESS_LINE_2,ADDRESS_LINE_3,CITY_NAME_1,STATE,ZIP_CODE,COUNTRY,UNIT_NO,UNIT_DESIGNATOR,ADDRESS_NUMBER,ADDRESS_NUMBER_SUFFIX,PRE_DIRECTION_CODE,STREET_NAME,STREET_TYPE_CODE,POST_DIRECTION_CODE,CITY_NAME,LOCATION_ZIP_CODE,TOTAL_ACTUAL_VALUE,TOTAL_ASSESSED_VALUE,TOTAL_NET_ACRES,ACCOUNT_STATUS,FEDERAL_ID_NO,LEGAL_DESCR,REDUCED_MILL_LEVY,REDUCED_TAX_RATE"
    ATTR_ACCUM_MODE = Only Use Result
    CLIP_TO_ENVELOPE = NO
    COMBINE_GEOM = Use Result
    DATASET = $(DB_EGDB_MSSQL_RO)
    FEATURETYPES = ENTAGE.ACCOUNT_FACT
    FORMAT = SQLSERVER
    INITIATOR_FIRST_OUTPUT = default
    INPUT_PORT_INITIATOR_CONNECTED = CONNECTED
    INTERACT = NONE
    MAX_FEATURES = 10
    ORDER_RESULTS = No
    OUTPUT_ADD_SCHEMA_ATTRIBUTES = NO
    OUTPUT_FEATURES_DISPLAY = Schema and Data Features
    OUTPUT_USE_SCHEMA_CACHE = YES
    READER_BEHAVIOR = SELECTFEATTYPES
    SQLSERVER_APPLICATION_INTENT = ReadWrite
    SQLSERVER_COMMAND_TIMEOUT = 30
    SQLSERVER_CREATE_FEATURE_TABLES_FROM_DATA = Yes
    SQLSERVER_MULTIPLE_SPATIAL_COLUMNS_MODE = Yes
    SQLSERVER_NAMED_CONNECTION = $(DB_EGDB_MSSQL_RO)
    SQLSERVER_NEW_MULTIGEOM_HANDLING = Yes
    SQLSERVER_PERSISTENT_CONNECTION = NO
    SQLSERVER_QUERY_FEATURE_TYPES_FOR_MERGE_FILTERS = Yes
    SQLSERVER_READ_CACHE_SIZE = 10
    SQLSERVER_USE_MAKE_VALID = NO
    SQLSERVER_USE_SEARCH_ENVELOPE = NO
    <SCHEMA> -> Tester_2
Tester_2
    BOOL_OP = OR
    TEST_MODE = TEST
Note: Created Date must have a value
Tester
    BOOL_OP = OR
    TEST_CLAUSE = CASE_INSENSITIVE_TEST _creation_instance ATTRIBUTE_HAS_A_VALUE ""
    TEST_MODE = CASE_INSENSITIVE_TEST
    PASSED -> AttributeManager
AttributeManager
Creator_2
    GEOMTYPE = No Geometry
    NUM = 1
    CREATED -> HTTPCaller
HTTPCaller
    AUTH_METHOD_TYPE = NC
    AUTH_NAMED_CONNECTION = FME Flow UA - Laurentp
    CLIENT_CERTIFICATE_TYPE = NONE
    CONNECTION_TIMEOUT_LENGTH = 60
    CUSTOM_HEADERS = Accept;application/json
    ERROR_ATTR = NeBranch
    FOLLOW_REDIRECTS = FOLLOW_WITH_GET
    HTTP_METHOD = GET
    INPUT_PORT_CONNECTED = CONNECTED
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://uaapps.douglas.co.us/fmeapiv4/jobs?status=success&limit=100&offset=0
    TRANSFER_TIMEOUT_LENGTH = 354
    USE_COOKIES = No
    VERIFY_SSL_CERTIFICATES = Yes
    AUTH_METHOD = Web Connection
